Attribute VB_Name = "ReadData"
' Chemtech - A Siemens Business ========================================================
'
'=======================================================================================
Option Explicit
' Desenvolvimento ======================================================================
' <iniciais>            Renan       <email>
'=======================================================================================
' Versões ==============================================================================
'
'
'
'=======================================================================================

Public Function getData(strAddress As String, Optional showMsgBoxes As Boolean = False) As String
'=======================================================================================
' Esta é a rotina que recebe a string de endereço e aciona a rotina correta para o carre
' gamento dos dados.
'---------------------------------------------------------------------------------------
' [showMsgBoxes] booleano que indica o desejo de apresentar msgboxes com informações
' [strAddress] string na forma "itemKey|propKey"
' Se o propKey começa com Z, trata-se de um endereço de rastreamento.
' Se o propKey começa com D, trata-se de uma referência com valor e unidade
' Se o propKey começa com U, trata-se de uma referência de unidade apenas
' Se o propKey começa com V, trata-se de uma referência de valor apenas
'---------------------------------------------------------------------------------------
' As propriedades que são calculadas aparecem na classe de propriedades 5.
' Referências de rastreamento tem a propKey começando com o caractere "Z" e neste caso,
' a propKey é uma string com o nome do campo de rastreamento (e.g. Nome_item)
'---------------------------------------------------------------------------------------
' < Histórico de revisões>
'=======================================================================================
'
' This function decides if your data is a normal one or a tracking one
    Dim Namez                                As Variant
    Dim propKey                              As Variant         'here the property primary key may assume the value of a trackingPropKey, which is a string
    Dim itemKey                              As Long
    Dim unitKey                              As Long
    Dim rs                                   As ADODB.Recordset

    ' Aqui vc pega as chaves de equipamento e valor da propriedade
    Namez = split(strAddress, breakString)
    itemKey = CLng(Namez(1))
    propKey = Namez(2)
    On Error Resume Next
    unitKey = Namez(3)    'ignoring the possible error for a tracking value
    On Error GoTo 0

    ' Transformando propKey em string
    Namez = CStr(propKey)
    propKey = Right(Namez, Len(Namez) - 1)            'Preparando a chave de propriedade

    ' aqui iniciamos o recordset
    Set rs = New ADODB.Recordset
    rs.CursorLocation = adUseClient

    ' Agora, você tem de checar o tipo de referência, e puxar o resultado com a rotina/opção correta;
    Select Case Left(Namez, 1)
        Case trackingChar
            getData = getTrackingDataFromAccess(itemKey, CStr(propKey), showMsgBoxes)

        Case unitOnlyChar
            getData = getDataFromAccess(itemKey, CLng(propKey), unitKey, 0, showMsgBoxes)

        Case valueOnlyChar
            getData = getDataFromAccess(itemKey, CLng(propKey), unitKey, 1, showMsgBoxes)

        Case unitAndValueChar
            getData = getDataFromAccess(itemKey, CLng(propKey), unitKey, 2, showMsgBoxes)

        Case calcChar
            getData = getCalculatedDataFromAccess(itemKey, CLng(propKey))

        Case Else
            Err.Raise vbObjectError + 440040, Description:="Não há especificação correta do endereço :" & strAddress

    End Select
End Function

Public Function getDataFromAccess(itemKey As Long, propKey As Long, unitKey As Long, refOption As Integer _
                                                                                     , Optional showMsgBoxes As Boolean = True)
'=======================================================================================
' < descrição da rotina >
'---------------------------------------------------------------------------------------
' < descrição dos argumentos>
'---------------------------------------------------------------------------------------
' < Observações >
'---------------------------------------------------------------------------------------
' < Histórico de revisões>
'=======================================================================================
'
    Dim strSQL                               As String
    Dim rs                                   As ADODB.Recordset
    Dim varValueFromDatabase                 As String
    Dim errorAction                          As Integer
    Dim tempValue                            As String
    Dim tempUnit                             As String

    ' Criando um recordset para receber a query
    Set rs = New ADODB.Recordset
    rs.CursorLocation = adUseClient

    ' Aqui entra o comando em SQL para fazer a query
    strSQL = " select VALOR_PROPRIEDADES.VALOR_PROP" & _
             " from VALOR_PROPRIEDADES inner join LINK_VALORES on VALOR_PROPRIEDADES.ID_VALOR = LINK_VALORES.ID_VALOR" & _
             " where ID_ITEM = " & itemKey & " And ID_TIPO_PROP = " & propKey

    ' abrindo a query
    rs.Open strSQL, gCnn

    On Error GoTo getDataFromAccess_Error
    Call assertGetData(rs, itemKey, propKey)          'This asserts no error in the query

    ' geting the value and the unit symbol
    tempValue = rs.Fields("VALOR_PROP").value
    If unitKey <> 0 Then
        tempValue = gUnitDef.convertValue(tempValue, propKey, unitKey, True)
        tempUnit = gUnitDef.getUnitSymbol(propKey, unitKey)
    End If

    ' The code here only happens if the thing ran without errors.
    Select Case refOption
        Case 0
            varValueFromDatabase = tempUnit
        Case 1
            varValueFromDatabase = tempValue
        Case 2
            varValueFromDatabase = tempValue & " " & tempUnit

    End Select

    getDataFromAccess = varValueFromDatabase

    Exit Function

getDataFromAccess_ExitSub:
    Exit Function

getDataFromAccess_Error:
    errorAction = handleMyError(showMsgBoxes)
    If Err.Number = vbObjectError + 100211 Or Err.Number = vbObjectError + _
       100212 Or Err.Number = vbObjectError + 100213 Then
        getDataFromAccess = Err.Description
    Else
        Select Case errorAction
            Case -1
                Stop
            Case 1
                Resume Next
            Case 2
                GoTo getDataFromAccess_ExitSub
            Case Else
                GoTo getDataFromAccess_ExitSub
        End Select
    End If

End Function

Public Function getTrackingDataFromAccess(itemKey As Long, propKey As Variant, Optional showMsgBoxes As Boolean = True)
'=======================================================================================
' < descrição da rotina >
'---------------------------------------------------------------------------------------
' < descrição dos argumentos>
'---------------------------------------------------------------------------------------
' < Observações >
'---------------------------------------------------------------------------------------
' < Histórico de revisões>
'=======================================================================================
'
    Dim strSQL                               As String
    Dim rs                                   As ADODB.Recordset
    Dim varValueFromDatabase                 As String
    Dim errorAction                          As Integer

    ' Aqui entra o comando em SQL para fazer a query
    ' Query string for the value
    strSQL = "select ITEM.NOME_ITEM, SUB_AREA.NOME_SUB_ARE, AREA.NOME_ARE, PLANTA.NOME_PLA, INDUSTRIAL.NOME_IND, UNIDADE_NEGOCIO.NOME_UNI " & _
             "from UNIDADE_NEGOCIO INNER JOIN ((((INDUSTRIAL INNER JOIN PLANTA ON INDUSTRIAL.ID_IND = PLANTA.ID_IND) INNER JOIN AREA ON " & _
             "PLANTA.ID_PLA = AREA.ID_PLA) INNER JOIN SUB_AREA ON AREA.ID_ARE = SUB_AREA.ID_ARE) INNER JOIN ITEM ON SUB_AREA.ID_SUB_ARE = ITEM.ID_SUB_ARE) ON UNIDADE_NEGOCIO.ID_UNI = INDUSTRIAL.ID_UNI " & _
             "where ITEM.ID_ITEM = " & itemKey

    ' Criando um recordset com o resultado da query
    Set rs = New ADODB.Recordset
    rs.CursorLocation = adUseClient
    rs.Open strSQL, gCnn

    On Error GoTo getTrackingDataFromAccess_Error
    Call assertGetTrackingData(rs, itemKey, propKey)

    varValueFromDatabase = rs.Fields(propKey).value
    getTrackingDataFromAccess = varValueFromDatabase

    Exit Function

getTrackingDataFromAccess_ExitSub:
    Exit Function

getTrackingDataFromAccess_Error:
    errorAction = handleMyError(showMsgBoxes)
    If Err.Number = vbObjectError + 100211 Or Err.Number = vbObjectError + _
       100212 Or Err.Number = vbObjectError + 100213 Then
        getTrackingDataFromAccess = Err.Description
    Else
        Select Case errorAction
            Case -1
                Stop
            Case 1
                Resume Next
            Case 2
                GoTo getTrackingDataFromAccess_ExitSub
            Case Else
                GoTo getTrackingDataFromAccess_ExitSub
        End Select
    End If
End Function

Private Function getCalculatedDataFromAccess(itemKey As Long, propKey As Long) As String
'=======================================================================================
' rotina que centraliza a obtenção das propriedades calculadas.
'---------------------------------------------------------------------------------------
' < descrição dos argumentos>
'---------------------------------------------------------------------------------------
' < Observações >
'---------------------------------------------------------------------------------------
' < Histórico de revisões>
'=======================================================================================
'
    Dim strPartial                           As String

    strPartial = ""

    Select Case propKey                               'Aqui eu faço a verificação dos casos especiais de propKeys
        Case 60
            strPartial = getDataFromAccess(itemKey, 46, 0, 1)
            strPartial = strPartial & Chr(34) & "-" & getDataFromAccess(itemKey, 61, 0, 1) & "-" & getTrackingDataFromAccess(itemKey, "NOME_ITEM")
            strPartial = strPartial & "-" & getDataFromAccess(itemKey, 38, 0, 1)

    End Select

    getCalculatedDataFromAccess = strPartial
End Function


Public Sub assertGetData(rs As ADODB.Recordset, itemKey As Long, propKey As Variant)
'=======================================================================================
' A rotina faz a asserção que o dado obtido do banco de dados é correto.
' a rotina checa se a query retornou um único valor. Se não, gera um erro com a descrição
' apropriada
'---------------------------------------------------------------------------------------
' < descrição dos argumentos>
'---------------------------------------------------------------------------------------
' < Observações >
'---------------------------------------------------------------------------------------
' < Histórico de revisões>
'=======================================================================================
'
    If rs.RecordCount = 1 Then
        If IsNull(rs.Fields("VALOR_PROP").value) Then
            Err.Raise vbObjectError + 100211, Description:="Erro! Valor da propriedade" & itemKey & "|" & propKey & " não está cadastrado (Null)"
        End If
    Else
        If rs.RecordCount > 1 Then
            Err.Raise vbObjectError + 100212, Description:="Erro! Valor da propriedade" & itemKey & "|" & propKey & " está dubplicado"
        Else
            Err.Raise vbObjectError + 100213, Description:="Erro! O par " & itemKey & "|" & propKey & " não está cadastrado"
        End If
    End If
End Sub


Public Sub assertGetTrackingData(rs As ADODB.Recordset, itemKey As Long, propKey As Variant)
'=======================================================================================
' A rotina faz a asserção que o dado obtido do banco de dados é correto.
' a rotina checa se a query retornou um único valor. Se não, gera um erro com a descrição
' apropriada
'---------------------------------------------------------------------------------------
' < descrição dos argumentos>
'---------------------------------------------------------------------------------------
' < Observações >
'---------------------------------------------------------------------------------------
' < Histórico de revisões>
'=======================================================================================
'
    If rs.RecordCount = 1 Then
        If IsNull(rs.Fields(propKey).value) Then
            Err.Raise vbObjectError + 100211, Description:="Erro! Valor da propriedade" & itemKey & "|" & propKey & " não está cadastrado (Null)"
        End If
    Else
        If rs.RecordCount > 1 Then
            Err.Raise vbObjectError + 100212, Description:="Erro! Valor da propriedade" & itemKey & "|" & propKey & " está dubplicado"
        Else
            Err.Raise vbObjectError + 100213, Description:="Erro! O par " & itemKey & "|" & propKey & " não está cadastrado"
        End If
    End If
End Sub

Public Function createAddress(itemKey As Long, propKey As Long, unitKey As Long, refOption As Integer) As String
    Dim strNewAddress                        As String
    ' checking which kind of reference to create
    If checkIfIsCalc(propKey) Then                    'checking if it is a calculated reference
        strNewAddress = breakString & itemKey & breakString & calcChar & propKey & breakString & 0
    Else
        Select Case refOption                         'choosing the non-calculated reference type.
            Case 0
                strNewAddress = breakString & itemKey & breakString & unitOnlyChar & propKey & breakString & unitKey
            Case 1
                strNewAddress = breakString & itemKey & breakString & valueOnlyChar & propKey & breakString & unitKey
            Case 2
                strNewAddress = breakString & itemKey & breakString & unitAndValueChar & propKey & breakString & unitKey
        End Select
    End If

    createAddress = strNewAddress
End Function

Public Function createTrackingAddress(itemKey As Long, propKey As Variant, unitKey As Long) As String
    createTrackingAddress = breakString & itemKey & breakString & trackingChar & propKey & breakString & unitKey
End Function

Attribute VB_Name = "autocadSpecific"

'#########
'Showing the manager
Sub showManager()
    frmRunManager.Show
End Sub

'##########################
' Getting the data from the database!
Sub getDataFromDatabase()

'Dim entity As AcadBlockReference
    Dim entity                     As Variant
    Dim addressForQuery            As String

    For Each entity In ThisDrawing.ModelSpace
        'Now, I test if the block is the CPNM
        If entity.ObjectName = "AcDbBlockReference" Then
            'If entity.Name Like "*CPNM*" Then

            ' This method gets all the attributes from the entity into an array of attribute objects.
            blockAttributes = entity.GetAttributes

            ' Now, I loop over the attributes to find the "LINKDATABASE" attribute, which gives us the address into the database
            For Each attrib In blockAttributes
                ' Testing if the current attribute is the database address
                If attrib.TagString = "LINKDATABASE" Then
                    ' getting the address string
                    addressForQuery = attrib.TextString

                    ' getting the value from the database
                    If addressForQuery <> "" Then valueFromDatabase = getData(addressForQuery)
                End If
            Next attrib

            ' Now, We have to find the "VALUE" Attribute and update it with the value we got from the database.
            For Each attrib In blockAttributes
                If attrib.TagString = "VALUE" Then
                    attrib.TextString = valueFromDatabase
                    sentinel = True
                End If
            Next attrib

            ' Updates the block in the drawing to show stuff
            entity.Update

            'End If
        End If
    Next entity
End Sub

Sub insertCpnmBlock(strAddress As String)

    Dim strName                    As String
    Dim varInsertionPoint          As Variant
    Dim dblX                       As Double
    Dim dblY                       As Double
    Dim dblZ                       As Double
    Dim dblRotation                As Double
    Dim newBlock                   As AcadBlockReference

    strName = "CPNM_1"
    dblX = 1#
    dblY = 1#
    dblZ = 1#
    dblRotation = 0#

    ' get imput from user
    ThisDrawing.Utility.InitializeUserInput 1
    varInsertionPoint = ThisDrawing.Utility.GetPoint(, vbCr & "Pick the insert point: ")

    ' create the object
    On Error Resume Next
    Set newBlock = ThisDrawing.ModelSpace.InsertBlock(varInsertionPoint, strName, dblX, dblY, dblZ, dblRotation)

    blockAttributes = newBlock.GetAttributes

    For Each attrib In blockAttributes
        If attrib.TagString = "LINKDATABASE" Then attrib.TextString = strAddress
    Next attrib

    If Err Then MsgBox "unable to insert this block"

End Sub

' ######################################
' Subs for the creation of docvar fields

Public Sub createReference(strItemName As String, strPropName As String, _
                           strUnitName As String, isTrack As Boolean, Optional refOption As Integer = 2)
' Database Path
Debug.Assert Application.Name = "AutoCAD"

    Dim itemKey                    As Long
    Dim propKey                    As Long
    Dim unitKey                    As Long
    Dim strNewAddress                 As String

    'checking if the property is calculated
    If isTrack Then
        itemKey = getItemKey(strItemName)

        Set colDictionary = createTrackingDictionary()
        itemTrackingPropKey = colDictionary(strPropName)

        strNewAddress = createTrackingAddress(itemKey, itemTrackingPropKey, 0)
    Else

        itemKey = getItemKey(strItemName)
        propKey = getPropKey(strPropName)
        unitKey = getUnitKey(strPropName, strUnitName)

        strNewAddress = createAddress(itemKey, CVar(propKey), unitKey, refOption)
    End If

    'Inserting the block with the correct address
    Call insertCpnmBlock(strNewAddress)

    'Updating all the blocks
    Call getDataFromDatabase

End Sub

Public Sub changeTheReferences(ltbOriginalItemName, ltbNewItemName, ckbColorChanges)
End Sub

Public Sub populateNewItem(ltbOriginalItemName, ltbNewItemName, strSubAreaName)
    MsgBox "não implementado ainda"
End Sub

Public Sub populateOriginalItem(ltbOriginalItemName, Optional strSubAreaName As String, Optional strItemClass As String)
End Sub

Attribute VB_Name = "autocadSpecificOpenFile"
Private Declare Function GetOpenFileName Lib "comdlg32.dll" Alias _
                                         "GetOpenFileNameA" (pOpenfilename As OPENFILENAME) As Long
Private Type OPENFILENAME
    lStructSize                    As Long
    hwndOwner                      As Long
    hInstance                      As Long
    lpstrFilter                    As String
    lpstrCustomFilter              As String
    nMaxCustFilter                 As Long
    nFilterIndex                   As Long
    lpstrFile                      As String
    nMaxFile                       As Long
    lpstrFileTitle                 As String
    nMaxFileTitle                  As Long
    lpstrInitialDir                As String
    lpstrTitle                     As String
    flags                          As Long
    nFileOffset                    As Integer
    nFileExtension                 As Integer
    lpstrDefExt                    As String
    lCustData                      As Long
    lpfnHook                       As Long
    lpTemplateName                 As String
End Type
Public Function ShowOpen(Filter As String, _
                         InitialDir As String, _
                         DialogTitle As String) As String
    Dim OFName                     As OPENFILENAME
    'Set the structure size
    OFName.lStructSize = Len(OFName)
    'Set the owner window
    OFName.hwndOwner = 0
    'Set the filter
    OFName.lpstrFilter = Filter
    'Set the maximum number of chars
    OFName.nMaxFile = 255
    'Create a buffer
    OFName.lpstrFile = Space(254)

    'Create a buffer
    OFName.lpstrFileTitle = Space$(254)
    'Set the maximum number of chars
    OFName.nMaxFileTitle = 255
    'Set the initial directory
    OFName.lpstrInitialDir = InitialDir
    'Set the dialog title
    OFName.lpstrTitle = DialogTitle
    'no extra flags
    OFName.flags = 0
    'Show the 'Open File' dialog
    If GetOpenFileName(OFName) Then
        ShowOpen = Trim(OFName.lpstrFile)
    Else
        ShowOpen = ""
    End If
End Function

Public Function getFileDialog()
    Dim Filter                     As String
    Dim InitialDir                 As String
    Dim DialogTitle                As String
    Dim OutputStr                  As String

    Filter = "Database Files (*.mdb)" + Chr$(0) + "*.mdb" + Chr$(0) + _
             "All Files (*.*)" + Chr$(0) + "*.*" + Chr$(0)
    InitialDir = "C:\Program Files\AutoCAD 2006\Sample"
    DialogTitle = "Open a MDB file"
    OutputStr = ShowOpen(Filter, InitialDir, DialogTitle)

    getFileDialog = OutputStr
End Function

Attribute VB_Name = "errorHandling"
' Chemtech - A Siemens Business ========================================================
'
'=======================================================================================
Option Explicit
' Desenvolvimento ======================================================================
' RR            Renan       renan.ranelli@chemtech.com.br
'=======================================================================================
' Versões ==============================================================================
'
'
'
'=======================================================================================

Public Function handleMyError(Optional showMsgBoxes As Boolean = True) As Integer
'=======================================================================================
'
'---------------------------------------------------------------------------------------
' [showMsgBoxes] - booleano que indica se serão apresentadas msgboxes com resultados do erro
'---------------------------------------------------------------------------------------
' Retorna: -1 para stop. (para a execução)
'           1 para resume next. (ignorar o erro e continuar a execução do código principal)
'           2 para goto ExitSub. (o equivalente ao "finally" do try/catch/except
'---------------------------------------------------------------------------------------
' < Histórico de revisões>
'=======================================================================================
'
    Dim intMyErrorNumber                     As Long

    'I extract my user defined error number.
    intMyErrorNumber = Err.Number - vbObjectError

    'If Err.Number = vbObjectError + 22000 Then
    Select Case intMyErrorNumber

        Case 100000    'No value in checkKeyness
            If showMsgBoxes Then MsgBox "An error has occurred and was caught" & _
               vbCr & vbCr & "Error number = " & Err.Number & _
               vbCr & vbCr & "Error description = " & Err.Description & _
               vbCr & vbCr & "problem at line: " & Erl, vbCritical


        Case 100001    'Duplicated values in checkKeyness
            MsgBox "An error has occurred and was caught" & _
                   vbCr & vbCr & "Error number = " & Err.Number & _
                   vbCr & vbCr & "Error description = " & Err.Description & _
                   vbCr & vbCr & "problem at line: " & Erl, vbCritical
            handleMyError = 1

        Case 22000    'This case corresponds to the test case
            MsgBox "Your test error was caught, and properly treated!" & vbCr & "YAY!!"
            handleMyError = 1

            ' ########
            ' GetData error handling
        Case 100211
            If showMsgBoxes Then MsgBox Err.Description
            handleMyError = 2
        Case 100212
            If showMsgBoxes Then MsgBox Err.Description
            handleMyError = 2
        Case 100213
            If showMsgBoxes Then MsgBox Err.Description
            handleMyError = 2

            ' collection creation error.
        Case 1121221
            If showMsgBoxes Then MsgBox Err.Description
            handleMyError = 1

            ' dimensionallity error.
        Case 175645
            If showMsgBoxes Then MsgBox Err.Description
            handleMyError = 2
            
        Case 554565
            If showMsgBoxes Then MsgBox Err.Description
            handleMyError = 2

        Case Else   'This case corresponds to an untreated error.
            MsgBox "An error has occurred and was caught, but not treated" & _
                   vbCr & vbCr & "Error number = " & Err.Number & _
                   vbCr & vbCr & "Error description = " & Err.Description & _
                   vbCr & vbCr & "problem at line: " & Erl, vbCritical
            handleMyError = -1
    End Select
End Function

Public Sub checkKeyness(rs As ADODB.Recordset)
'=======================================================================================
' < descrição da rotina >
'---------------------------------------------------------------------------------------
' [rs] recordset que vem de uma query
'---------------------------------------------------------------------------------------
' < Observações >
'---------------------------------------------------------------------------------------
' < Histórico de revisões>
'=======================================================================================
'
' This sub checks if there is more than one, or more than one, records in the recordset, where it should have a single record in it.
    If rs.EOF = True Then
        Err.Raise vbObjectError + 100000, Description:="The query returned no value!"
    Else
        If rs.RecordCount > 1 Then
            Err.Raise vbObjectError + 100001, "The query returned no value!"
        End If
    End If
End Sub

Attribute VB_Name = "frmChangeItemReferences"
Attribute VB_Base = "0{79C27B75-CB7A-442E-A65A-EEDFCCEEE9CF}{959058F6-ADF2-427D-882A-ED6354C8D07A}"
Attribute VB_GlobalNameSpace = False
Attribute VB_Creatable = False
Attribute VB_PredeclaredId = True
Attribute VB_Exposed = False
Attribute VB_TemplateDerived = False
Attribute VB_Customizable = False

Private Sub userform_initialize()
' This sub populates the combobox with the names of the referenced items in the documents
    Call populateOriginalItem(ltbOriginalItemName)

    Call populateItemClass(cmbItemClassOrig)

    Call populateSubArea(cmbSubAreaOrig)
    Call populateSubArea(cmbSubAreaNew)

End Sub

' ##############
' Buttons

Private Sub btnChangeReferences_Click()
' This sub will then issue the command to change the references
    If ltbOriginalItemName.value <> Empty And ltbNewItemName.value <> Empty Then
        Call changeTheReferences(ltbOriginalItemName.value, ltbNewItemName.value, ckbColorChanges.value)
        Unload Me
    Else
        MsgBox "Especificação incompleta"
    End If
End Sub

' End of buttons
' ##############

' ##############
' Populating

Private Sub cmbItemClassOrig_Change()
    ltbOriginalItemName.Clear
    Call populateOriginalItem(ltbOriginalItemName, cmbItemClassOrig.value, cmbSubAreaOrig.value)
End Sub

Private Sub cmbSubAreaOrig_Change()
    ltbOriginalItemName.Clear
    Call populateOriginalItem(ltbOriginalItemName, cmbItemClassOrig.value, cmbSubAreaOrig.value)
End Sub

Private Sub cmbSubAreaNew_Change()
    ltbNewItemName.Clear
    If ltbOriginalItemName.value <> Empty Then
        Call populateNewItem(ltbOriginalItemName.value, ltbNewItemName, cmbSubAreaNew.value)
    End If
End Sub

Private Sub ltbOriginalItemName_Change()
' This sub populates the newItem combobox in accordance with the items type in the originalItem combobox
    ltbNewItemName.Clear
    If ltbOriginalItemName.value <> Empty Then
        Call populateNewItem(ltbOriginalItemName.value, ltbNewItemName, cmbSubAreaNew.value)
    End If
End Sub

' End of Populating
' ##############

Attribute VB_Name = "frmInsertBigCrossRef"
Attribute VB_Base = "0{A39FFFCE-8EBE-4CF6-8435-25A3D7A5B377}{7CD93488-2DCF-4B91-84FD-1171C36A04EB}"
Attribute VB_GlobalNameSpace = False
Attribute VB_Creatable = False
Attribute VB_PredeclaredId = True
Attribute VB_Exposed = False
Attribute VB_TemplateDerived = False
Attribute VB_Customizable = False

Private txbNewValue                As TextBox         'This is just a fix. Without it, I cant use the lump of code.
Private refOption                  As Integer

Private Sub userform_initialize()
' populando para a aba de referência a valor
    Call populateItemType(ltbItemType)
    Call populateItemClass(cmbItemClass)
    Call populateSubArea(cmbSubArea)
    Call populatePropClass(cmbPropClass)
    ' populando para a aba de referência a rastreamento
    Call populateItemClass(cmbItemClassTrack)
    Call populateSubArea(cmbSubAreaTrack)
    Call populateItemType(ltbItemTypeTrack)

    ' iniciando a opção padrão de unidade & valor.
    opbValueAndUnit.value = True
End Sub

'#################
' Buttons

Private Sub btnCreateReference_Click()
' This sub creates the reference by using the values defined in the comboboxes
    Me.Hide
    If (ltbItemName.value <> Empty And ltbPropName.value <> Empty _
        And (ltbUnitName.ListCount = 0 Or (ltbUnitName.value <> Empty And ltbUnitName <> Empty))) Then
        Call createReference(ltbItemName.value, ltbPropName.value, ltbUnitName.value, False, refOption)
    Else
        MsgBox "Faltam items para especificar!"
    End If
    Me.Show
End Sub

Private Sub btnCreateTrackingReference_Click()
' this sub creates a tracking reference
    Me.Hide
    Call createReference(ltbItemNameTrack.value, ltbPropNameTrack.value, "0", True)
    Me.Show
End Sub

' Subs for the selection of the reference style to be inserted
Private Sub opbValue_Click()
    refOption = 1
End Sub

Private Sub opbUnit_Click()
    refOption = 0
End Sub

Private Sub opbValueAndUnit_Click()
    refOption = 2
End Sub

' End of buttons
' ##############

' ####################################################
' Start of the property location lump of code

Private Sub ckbExistantProps_Click()
    If ckbExistantProps.value = True Then             'O click resolve antes da mudança.
        If ltbItemName.value <> Empty Then
            ltbPropName.Clear
            Call populateExistantProps(ltbItemName.value, ltbPropName, cmbPropClass.value)
        End If
    Else
        If ltbItemType.value <> Empty Then
            ltbPropName.Clear
            Call populateProps(ltbItemType.value, ltbPropName, cmbPropClass.value)
        End If
    End If
End Sub

Private Sub cmbItemClass_Change()
    ltbItemType.Clear
    Call populateItemType(ltbItemType, cmbItemClass.value)
End Sub

Private Sub ltbItemType_Change()
' This sub populates item names and property names on their comboboxes
    ltbItemName.Clear
    ltbPropName.Clear
    txbCurrentValue.Text = ""
    If Not txbNewValue Is Nothing Then txbNewValue.Text = ""
    If ltbItemType.value <> Empty Then
        If ckbExistantProps.value = False Then
            Call populateItems(ltbItemType.value, ltbItemName, cmbSubArea.value)
            Call populateProps(ltbItemType.value, ltbPropName, cmbPropClass.value)
        Else
            Call populateItems(ltbItemType.value, ltbItemName, cmbSubArea.value)
        End If
    End If
End Sub

Private Sub ltbPropName_Change()
    ltbUnitName.Clear
    Call showCurrentData
    If ltbPropName.value <> Empty Then
        Call populateUnits(ltbPropName.value, ltbUnitName)
    End If
End Sub

Private Sub ltbUnitName_Change()
    Call showCurrentData
End Sub

Private Sub ltbItemName_Change()
' This sub populates item names and property names on their comboboxes
    Call showCurrentData
    If ckbExistantProps.value And ltbItemName.value <> Empty Then
        ltbPropName.Clear
        Call populateExistantProps(ltbItemName.value, ltbPropName, cmbPropClass.value)
    End If
End Sub

Private Sub cmbSubArea_Change()
    If ltbItemType.value <> Empty Then
        ltbItemName.Clear
        Call populateItems(ltbItemType.value, ltbItemName, cmbSubArea.value)
    End If
End Sub

Private Sub cmbPropClass_Change()
    ltbPropName.Clear
    If ltbItemType.value <> Empty Then
        If ckbExistantProps.value And ltbItemName.value <> Empty Then
            Call populateExistantProps(ltbItemName.value, ltbPropName, cmbPropClass.value)
        Else
            Call populateProps(ltbItemType.value, ltbPropName, cmbPropClass.value)
        End If
    End If
End Sub

' End of the normal property lump of code
' ####################################################

' ####################################################
' Start of the Tracking property location lump of code

Private Sub cmbItemClassTrack_Change()
    ltbItemTypeTrack.Clear
    Call populateItemType(ltbItemTypeTrack, cmbItemClassTrack.value)
End Sub

Private Sub ltbItemTypeTrack_Change()
' This sub populates item names and tracking property names on their comboboxes
    ltbItemNameTrack.Clear
    ltbPropNameTrack.Clear
    txbCurrentValue.Text = ""
    If Not txbNewValue Is Nothing Then txbNewValue.Text = ""
    If ltbItemTypeTrack.value <> Empty Then
        Call populateItems(ltbItemTypeTrack.value, ltbItemNameTrack, cmbSubArea.value)
        Call populateTrackingProps(ltbItemTypeTrack.value, ltbPropNameTrack)
    End If
End Sub

Private Sub cmbSubAreaTrack_Change()
    If ltbItemTypeTrack.value <> Empty Then
        ltbItemNameTrack.Clear
        Call populateItems(ltbItemTypeTrack.value, ltbItemNameTrack, cmbSubAreaTrack.value)
    End If
End Sub

Private Sub ltbItemNameTrack_Click()
    Call showCurrentData
End Sub

Private Sub ltbPropNameTrack_Click()
    Call showCurrentData
End Sub

' End of the tracking property location lump of code
' ####################################################

'######
' Auxiliary

Private Sub showCurrentData()
    Dim propKey                    As Variant         'propKey may receive track or normal type of reference.
    Dim itemKey                    As Long
    Dim unitKey                    As Long
    Dim colDictionary              As Collection

    txbCurrentValue.value = ""
    txbCurrentValueTrack.value = ""

    If (ltbPropName.value <> Empty) And (ltbItemName.value <> Empty) Then
        propKey = getPropKey(ltbPropName.value)
        If (ltbUnitName.value <> Empty) Or getDimKey(CLng(propKey)) = 0 Then
            Set colDictionary = createTrackingDictionary

            itemKey = getItemKey(ltbItemName.value)
            propKey = getPropKey(ltbPropName.value)
            If Not IsNull(ltbUnitName.value) Then _
               unitKey = getUnitKey(ltbPropName.value, ltbUnitName.value)

            txbCurrentValue.value = getDataFromAccess(itemKey, CLng(propKey), unitKey, 2, False)    'This "2" makes the unit show up in the value
        End If
    End If

    If ltbPropNameTrack.value <> Empty And ltbItemNameTrack.value <> Empty Then
        Set colDictionary = createTrackingDictionary

        itemKey = getItemKey(ltbItemNameTrack.value)
        propKey = colDictionary(ltbPropNameTrack.value)
        txbCurrentValueTrack.value = getTrackingDataFromAccess(itemKey, CStr(propKey), False)
    End If
End Sub

Attribute VB_Name = "frmInsertDataManually"
Attribute VB_Base = "0{91D74AD8-BB30-4BF0-921A-AC1B1FC674A4}{E201241E-5C6A-46BC-B5AD-93EB7C26B3C0}"
Attribute VB_GlobalNameSpace = False
Attribute VB_Creatable = False
Attribute VB_PredeclaredId = True
Attribute VB_Exposed = False
Attribute VB_TemplateDerived = False
Attribute VB_Customizable = False

Private Sub userform_initialize()
' populando para a aba de referência a valor
    Call populateItemType(ltbItemType)
    Call populateItemClass(cmbItemClass)
    Call populateSubArea(cmbSubArea)
    Call populatePropClass(cmbPropClass)
    ' populando para a aba de referência a rastreamento
    Call populateItemClass(cmbItemClassTrack)
    Call populateSubArea(cmbSubAreaTrack)
    Call populateItemType(ltbItemTypeTrack)
    ' populando a sub para criação do item
    Call populateSubArea(ltbSubArea)
    Call populateItemClass(cmbItemClassCreate)
    Call populateItemType(ltbItemTypeCreate)
End Sub

' ############
' BUTTONS

Private Sub btnExportData_Click()
' This sub is used to export data to the database, given the names especification
    If Not IsNull(ltbUnitName.value) Then
        Call exportSingleData(ltbItemName.value, ltbPropName.value, txbValue.value, ltbUnitName.value, True)
    Else
        Call exportSingleData(ltbItemName.value, ltbPropName.value, txbValue.value, "", True)
    End If
    MsgBox "Dado exportado com sucesso!"
End Sub

Private Sub btnChangeTrackingProperty_Click()
    If txbNewValue.value <> "" Then
        Call changeTrackingData(ltbItemNameTrack.value, ltbPropNameTrack.value, txbNewValue.value)
        If Not Err Then MsgBox "Referência de rastreamento alterada com sucesso"
        
        ltbItemNameTrack.Clear
        Call populateItems(ltbItemTypeTrack.value, ltbItemNameTrack, cmbSubArea.value)
    End If
End Sub

Private Sub btnCreateNewItem_Click()
' This sub creates a new item using the defined values in their comboboxes
    If checkItemExistance(txbNewItemName.value) = False Then
        Call createItem(txbNewItemName.value, ltbItemTypeCreate.value, ltbSubArea.value)
        MsgBox "Item criado com sucesso!"
    Else
        MsgBox "Já existe um Item com este nome cadastrado!"
    End If
    'Unload Me
End Sub

' End of buttons
' ##############

' ##############
' create
Private Sub cmbItemClassCreate_Change()
    ltbItemTypeCreate.Clear
    Call populateItemType(ltbItemTypeCreate, cmbItemClassCreate.value)
End Sub

' End of create
' ##############

' ####################################################
' Start of the property location lump of code

Private Sub ckbExistantProps_Click()
    If ckbExistantProps.value = True Then             'O click resolve antes da mudança.
        If ltbItemName.value <> Empty Then
            ltbPropName.Clear
            Call populateExistantProps(ltbItemName.value, ltbPropName, cmbPropClass.value)
        End If
    Else
        If ltbItemType.value <> Empty Then
            ltbPropName.Clear
            Call populateProps(ltbItemType.value, ltbPropName, cmbPropClass.value)
        End If
    End If
End Sub

Private Sub cmbItemClass_Change()
    ltbItemType.Clear
    Call populateItemType(ltbItemType, cmbItemClass.value)
End Sub

Private Sub ltbItemType_Change()
' This sub populates item names and property names on their comboboxes
    ltbItemName.Clear
    ltbPropName.Clear
    txbCurrentValue.Text = ""
    If Not txbNewValue Is Nothing Then txbNewValue.Text = ""
    If ltbItemType.value <> Empty Then
        If ckbExistantProps.value = False Then
            Call populateItems(ltbItemType.value, ltbItemName, cmbSubArea.value)
            Call populateProps(ltbItemType.value, ltbPropName, cmbPropClass.value)
        Else
            Call populateItems(ltbItemType.value, ltbItemName, cmbSubArea.value)
        End If
    End If
End Sub

Private Sub ltbPropName_Change()
    ltbUnitName.Clear
    Call showCurrentData
    If ltbPropName.value <> Empty Then
        Call populateUnits(ltbPropName.value, ltbUnitName)
    End If
End Sub

Private Sub ltbUnitName_Change()
    Call showCurrentData
End Sub

Private Sub ltbItemName_Change()
' This sub populates item names and property names on their comboboxes
    Call showCurrentData
    If ckbExistantProps.value And ltbItemName.value <> Empty Then
        ltbPropName.Clear
        Call populateExistantProps(ltbItemName.value, ltbPropName, cmbPropClass.value)
    End If
End Sub

Private Sub cmbSubArea_Change()
    If ltbItemType.value <> Empty Then
        ltbItemName.Clear
        Call populateItems(ltbItemType.value, ltbItemName, cmbSubArea.value)
    End If
End Sub

Private Sub cmbPropClass_Change()
    ltbPropName.Clear
    If ltbItemType.value <> Empty Then
        If ckbExistantProps.value And ltbItemName.value <> Empty Then
            Call populateExistantProps(ltbItemName.value, ltbPropName, cmbPropClass.value)
        Else
            Call populateProps(ltbItemType.value, ltbPropName, cmbPropClass.value)
        End If
    End If
End Sub

' End of the normal property lump of code
' ####################################################

' ####################################################
' Start of the Tracking property location lump of code

Private Sub cmbItemClassTrack_Change()
    ltbItemTypeTrack.Clear
    Call populateItemType(ltbItemTypeTrack, cmbItemClassTrack.value)
End Sub

Private Sub ltbItemTypeTrack_Change()
' This sub populates item names and tracking property names on their comboboxes
    ltbItemNameTrack.Clear
    ltbPropNameTrack.Clear
    txbCurrentValue.Text = ""
    If Not txbNewValue Is Nothing Then txbNewValue.Text = ""
    If ltbItemTypeTrack.value <> Empty Then
        Call populateItems(ltbItemTypeTrack.value, ltbItemNameTrack, cmbSubArea.value)
        Call populateTrackingProps(ltbItemTypeTrack.value, ltbPropNameTrack)
    End If
End Sub

Private Sub cmbSubAreaTrack_Change()
    If ltbItemTypeTrack.value <> Empty Then
        ltbItemNameTrack.Clear
        Call populateItems(ltbItemTypeTrack.value, ltbItemNameTrack, cmbSubAreaTrack.value)
    End If
End Sub

Private Sub ltbItemNameTrack_Click()
    Call showCurrentData
End Sub

Private Sub ltbPropNameTrack_Click()
    Call showCurrentData
End Sub

' End of the tracking property location lump of code
' ####################################################

'######
' Auxiliary

Private Sub showCurrentData()
    Dim propKey                    As Variant         'propKey may receive track or normal type of reference.
    Dim itemKey                    As Long
    Dim unitKey                    As Long
    Dim colDictionary              As Collection

    txbCurrentValue.value = ""
    txbCurrentValueTrack.value = ""

    If (ltbPropName.value <> Empty) And (ltbItemName.value <> Empty) Then
        propKey = getPropKey(ltbPropName.value)
        If (ltbUnitName.value <> Empty) Or getDimKey(CLng(propKey)) = 0 Then
            Set colDictionary = createTrackingDictionary

            itemKey = getItemKey(ltbItemName.value)
            propKey = getPropKey(ltbPropName.value)
            If Not IsNull(ltbUnitName.value) Then _
               unitKey = getUnitKey(ltbPropName.value, ltbUnitName.value)

            txbCurrentValue.value = getDataFromAccess(itemKey, CLng(propKey), unitKey, 2, False)    'This "2" makes the unit show up in the value
        End If
    End If

    If ltbPropNameTrack.value <> Empty And ltbItemNameTrack.value <> Empty Then
        Set colDictionary = createTrackingDictionary

        itemKey = getItemKey(ltbItemNameTrack.value)
        propKey = colDictionary(ltbPropNameTrack.value)
        txbCurrentValueTrack.value = getTrackingDataFromAccess(itemKey, CStr(propKey), False)
    End If
End Sub

Attribute VB_Name = "frmRunManager"
Attribute VB_Base = "0{FA5FE850-8DCF-4CE0-AA0D-4E0422D822A3}{5795BBA1-4223-46BB-B177-18954B0FD182}"
Attribute VB_GlobalNameSpace = False
Attribute VB_Creatable = False
Attribute VB_PredeclaredId = True
Attribute VB_Exposed = False
Attribute VB_TemplateDerived = False
Attribute VB_Customizable = False

Private Sub userform_initialize()
    Call createGlobalUnitDefinitionObject

    Set gCnn = defineDatabaseConnection(-1)
    On Error Resume Next
    gCnn.Open
    If Err Then MsgBox "Você precisa configurar uma conexão a um banco de dados"
    On Error GoTo 0
End Sub

Private Sub userform_Terminate()
    MsgBox "Terminando a seção" & vbCr & vbCr & "Obrigado por usar o Copy Paste Nunca Mais"
    'If gCnn.State = 1 Then gCnn.Close 'essa linha deve ser descomentada quando for lançada
End Sub

Private Sub btnChangeReference_Click()
' This sub activates the form to create references
    Me.Hide
    frmChangeItemReferences.Show
    Unload Me
End Sub

Private Sub btnCreateConnection_Click()
' This sub creates the connection to the database
    If gCnn.State = adStateOpen Then
        gCnn.Close
    End If

    If gCnn.State = adStateClosed Then
        Set gCnn = defineDatabaseConnection(1)
        gCnn.Open
    Else
        MsgBox "there is a problem with the database connection object."
    End If
End Sub

Private Sub btnInsertSingleValue_Click()
' This sub activates the form to create references
    Me.Hide
    frmInsertDataManually.Show
    Me.Show
End Sub

Private Sub btnNewReference_Click()
' This sub activates the form to create references
    Me.Hide
    frmInsertBigCrossRef.Show
    Unload Me
End Sub

Private Sub btnDownloadData_Click()
    Call getDataFromDatabase
    If Not Err Then MsgBox "Download dos dados do Database: Sucesso!"
    Unload Me
End Sub

Private Sub cmbCriaCompart_Click()
    Me.Hide
    frmShareProps.Show
    Me.Show
End Sub

Attribute VB_Name = "frmShareProps"
Attribute VB_Base = "0{5C77F5F6-1687-4E26-903E-6324818890B1}{7367C042-9931-46B5-B997-FA571B97C13A}"
Attribute VB_GlobalNameSpace = False
Attribute VB_Creatable = False
Attribute VB_PredeclaredId = True
Attribute VB_Exposed = False
Attribute VB_TemplateDerived = False
Attribute VB_Customizable = False

Private txbNewValue1                         As TextBox
Private txbNewValue2                         As TextBox
Private breakQueue(100, 4)                   As Variant
Dim objShareQueue                            As shareQueue
Dim objBreakQueue                            As shareQueue

'###########
' INIT
Private Sub userform_initialize()
' This sub populates the item type combobox
    Call populateItemType(ltbItemType1)
    Call populateItemType(ltbItemType2)
    Call populateItemType(ltbItemTypeBreak)

    Call populateItemClass(cmbItemClass1)
    Call populateItemClass(cmbItemClass2)
    Call populateItemClass(cmbItemClassBreak)

    Call populateSubArea(cmbSubArea1)
    Call populateSubArea(cmbSubArea2)
    Call populateSubArea(cmbSubAreaBreak)

    Call populatePropClass(cmbPropClass1)
    Call populatePropClass(cmbPropClass2)
    Call populatePropClass(cmbPropClassBreak)

    Set objShareQueue = New shareQueue
    Set objBreakQueue = New shareQueue
End Sub

'##################################
' BUTTONS

'#####
' Buttons at share

Private Sub btnCreateShare_Click()
' this sub creates the sharing given the options at the comboboxes
    Dim j                                    As Integer
    Dim strItemName1                         As String
    Dim strItemName2                         As String
    Dim strPropName1                         As String
    Dim strPropName2                         As String
    Dim arrCollection                        As Collection
    Dim varArray()                           As Variant

    Set arrCollection = objShareQueue.sharesCollection

    For j = 1 To objShareQueue.countShares

        varArray = arrCollection(j)

        strItemName1 = varArray(0)
        strPropName1 = varArray(1)
        strItemName2 = varArray(2)
        strPropName2 = varArray(3)

        Call createSharing(strItemName1, strPropName1, strItemName2, strPropName2)
    Next j

    MsgBox "Execução Completada"
End Sub

Private Sub btnAddToList_Click()

    Dim dimKey1                              As Long
    Dim dimKey2                              As Long
    ' checking if the adding is valid
    If ltbItemName1.value <> Empty And ltbItemName2.value <> Empty _
       And ltbPropName1.value <> Empty And ltbPropName2.value <> Empty Then

        dimKey1 = getDimKey(getPropKey(ltbPropName1.value))
        dimKey2 = getDimKey(getPropKey(ltbPropName2.value))

        If dimKey1 = dimKey2 Then
            Call objShareQueue.enqueue(ltbItemName1.value, ltbPropName1.value, ltbItemName2.value, ltbPropName2.value)
            Call addToShareList(ltbCreationQueue, ltbItemName1.value, ltbItemName2.value, ltbPropName1.value, ltbPropName2.value)
        Else
            MsgBox "Você está tentando adicionar à lista propriedades cujas dimensões não concordam."
        End If
    Else
        MsgBox "especificação incompleta"
    End If
End Sub

Private Sub btnCleanList_Click()
    objShareQueue.Clear
    ltbCreationQueue.Clear
End Sub

Private Sub btnRemoveFromList_Click()
    Dim indexClicked                         As Integer
    Dim j                                    As Integer
    Dim k                                    As Integer

    If objShareQueue.countShares > 0 And ltbCreationQueue.ListIndex + 1 <> Empty Then

        indexClicked = Int(ltbCreationQueue.ListIndex / 3)

        ' deleting from the listbox
        Call removeFromShareList(ltbCreationQueue, indexClicked)
        ' dequeuing the clicked value
        objShareQueue.dequeue (indexClicked)
    End If
End Sub

Private Sub btnSaveList_Click()
    Call checkShareCollection(objShareQueue.sharesCollection)
    MsgBox "execução completa"
End Sub

Private Sub btnLoadShare_Click()

    Dim varArray                             As Variant
    Dim strPropName1                         As String
    Dim strPropName2                         As String
    Dim strItemName1                         As String
    Dim strItemName2                         As String
    Dim shareCollection                      As Collection
    Dim j                                    As Integer


    If ltbSavedShares.value <> Empty And ltbItemName1.value <> Empty And ltbItemName2.value <> Empty Then
        Set objShareQueue = loadShareCollection(ltbSavedShares.value, ltbItemName1.value, ltbItemName2.value)
        Set shareCollection = objShareQueue.sharesCollection

        For j = 1 To shareCollection.Count
            varArray = shareCollection(j)

            strItemName1 = varArray(0)
            strPropName1 = varArray(1)
            strItemName2 = varArray(2)
            strPropName2 = varArray(3)

            Call addToShareList(ltbCreationQueue, strItemName1, strItemName2, strPropName1, strPropName2)
        Next j

    Else
        MsgBox "especificação incompleta"
    End If
End Sub

'#####
'Buttons at break
Private Sub btnBreakShare_Click()
' this sub creates the sharing given the options at the comboboxes
    Dim j                                    As Integer
    Dim strItemName1                         As String
    Dim strItemName2                         As String
    Dim strPropName1                         As String
    Dim strPropName2                         As String
    Dim arrCollection                        As Collection
    Dim varArray()                           As Variant

    Set arrCollection = objBreakQueue.sharesCollection

    For j = 1 To objBreakQueue.countShares

        varArray = arrCollection(j)

        strItemName1 = varArray(0)
        strPropName1 = varArray(1)
        strItemName2 = varArray(2)
        strPropName2 = varArray(3)

        Call breakSharing(strItemName1, strPropName1, strItemName2, strPropName2)
    Next j

    MsgBox "Execução Completada"
End Sub

Private Sub btnAddToListBreak_Click()

    If ltbItemNameOrig.value <> Empty And ltbPropNameOrig.value <> Empty _
       And ltbItemNameComp.value <> Empty And txbPropNameComp.value <> Empty Then
        Call objBreakQueue.enqueue(ltbItemNameOrig.value, ltbPropNameOrig.value, ltbItemNameComp.value, txbPropNameComp.value)
        Call addToShareList(ltbBreakQueue, ltbItemNameOrig.value, ltbPropNameOrig.value, ltbItemNameComp.value, txbPropNameComp.value)
    Else
        MsgBox "especificação incompleta"
    End If
End Sub

Private Sub btnCleanListBreak_Click()
    objBreakQueue.Clear
    ltbBreakQueue.Clear
End Sub

Private Sub btnRemoveFromListBreak_Click()
    Dim indexClicked                         As Integer
    Dim j                                    As Integer
    Dim k                                    As Integer

    If objBreakQueue.countShares > 0 And ltbBreakQueue.ListIndex + 1 <> Empty Then

        indexClicked = Int(ltbBreakQueue.ListIndex / 3)

        ' deleting from the listbox
        Call removeFromShareList(ltbBreakQueue, indexClicked)
        ' dequeuing the clicked value
        objBreakQueue.dequeue (indexClicked)
    End If
End Sub

Private Sub btnLoadBreak_Click()

    Dim varArray                             As Variant
    Dim strPropName1                         As String
    Dim strPropName2                         As String
    Dim strItemName1                         As String
    Dim strItemName2                         As String
    Dim shareCollection                      As Collection
    Dim j                                    As Integer


    If ltbSavedSharesBreak.value <> Empty And ltbItemNameComp.value <> Empty And ltbItemNameOrig.value <> Empty Then
        Set objBreakQueue = loadShareCollection(ltbSavedSharesBreak.value, ltbItemNameOrig.value, ltbItemNameComp.value)
        Set shareCollection = objBreakQueue.sharesCollection

        For j = 1 To shareCollection.Count
            varArray = shareCollection(j)

            strItemName1 = varArray(0)
            strPropName1 = varArray(1)
            strItemName2 = varArray(2)
            strPropName2 = varArray(3)

            Call addToShareList(ltbBreakQueue, strItemName1, strItemName2, strPropName1, strPropName2)
        Next j

    Else
        MsgBox "especificação incompleta"
    End If
End Sub

' ####################################################
' Start of the property location lump of code <frame 1>

Private Sub ckbExistantProps1_Click()
    If ckbExistantProps1.value = True Then            'O click resolve antes da mudança.
        If ltbItemName1.value <> Empty Then
            ltbPropName1.Clear
            Call populateExistantProps(ltbItemName1.value, ltbPropName1, cmbPropClass1.value)
        End If
    Else
        If ltbItemType1.value <> Empty Then
            ltbPropName1.Clear
            Call populateProps(ltbItemType1.value, ltbPropName1, cmbPropClass1.value)
        End If
    End If
End Sub

Private Sub cmbItemClass1_Change()
    ltbItemType1.Clear
    Call populateItemType(ltbItemType1, cmbItemClass1.value)
End Sub

Private Sub ltbItemType1_Change()
' This sub populates item names and property names on their comboboxes
    ltbItemName1.Clear
    ltbPropName1.Clear
    txbCurrentValue1.Text = ""
    If Not txbNewValue1 Is Nothing Then txbNewValue1.Text = ""
    If ltbItemType1.value <> Empty Then
        If ckbExistantProps1.value = False Then
            Call populateItems(ltbItemType1.value, ltbItemName1, cmbSubArea1.value)
            Call populateProps(ltbItemType1.value, ltbPropName1, cmbPropClass1.value)
        Else
            Call populateItems(ltbItemType1.value, ltbItemName1, cmbSubArea1.value)
        End If
    End If

    ltbSavedShares.Clear
    If ltbItemType1.value <> Empty And ltbItemType2.value <> Empty Then
        Call populateSavedShares(ltbSavedShares, ltbItemType1.value, ltbItemType2.value)
    End If
End Sub

Private Sub ltbItemName1_Change()
' This sub populates item names and property names on their comboboxes
    Call showCurrentData1
    If ckbExistantProps1.value And ltbItemName1.value <> Empty Then
        ltbPropName1.Clear
        Call populateExistantProps(ltbItemName1.value, ltbPropName1, cmbPropClass1.value)
    End If
End Sub

Private Sub ltbPropName1_Change()
    Call showCurrentData1
End Sub

Private Sub cmbSubArea1_Change()
    If ltbItemType1.value <> Empty Then
        ltbItemName1.Clear
        Call populateItems(ltbItemType1.value, ltbItemName1, cmbSubArea1.value)
    End If
End Sub

Private Sub cmbPropClass1_Change()
    ltbPropName1.Clear
    If ltbItemType1.value <> Empty Then
        If ckbExistantProps1.value And ltbItemName1.value <> Empty Then
            Call populateExistantProps(ltbItemName1.value, ltbPropName1, cmbPropClass1.value)
        Else
            Call populateProps(ltbItemType1.value, ltbPropName1, cmbPropClass1.value)
        End If
    End If
End Sub

' End of the normal property lump of code <frame 1>
' ####################################################

' ####################################################
' Start of the property location lump of code <frame 2>

Private Sub ckbExistantProps2_Click()
    If ckbExistantProps2.value = True Then            'O click resolve antes da mudança.
        If ltbItemName2.value <> Empty Then
            ltbPropName2.Clear
            Call populateExistantProps(ltbItemName2.value, ltbPropName2, cmbPropClass2.value)
        End If
    Else
        If ltbItemType2.value <> Empty Then
            ltbPropName2.Clear
            Call populateProps(ltbItemType2.value, ltbPropName2, cmbPropClass2.value)
        End If
    End If
End Sub

Private Sub cmbItemClass2_Change()
    ltbItemType2.Clear
    Call populateItemType(ltbItemType2, cmbItemClass2.value)
End Sub

Private Sub ltbItemType2_Change()
' This sub populates item names and property names on their comboboxes
    ltbItemName2.Clear
    ltbPropName2.Clear
    txbCurrentValue2.Text = ""
    If Not txbNewValue2 Is Nothing Then txbNewValue2.Text = ""
    If ltbItemType2.value <> Empty Then
        If ckbExistantProps2.value = False Then
            Call populateItems(ltbItemType2.value, ltbItemName2, cmbSubArea2.value)
            Call populateProps(ltbItemType2.value, ltbPropName2, cmbPropClass2.value)
        Else
            Call populateItems(ltbItemType2.value, ltbItemName2, cmbSubArea2.value)
        End If
    End If

    ltbSavedShares.Clear
    If ltbItemType1.value <> Empty And ltbItemType2.value <> Empty Then
        Call populateSavedShares(ltbSavedShares, ltbItemType1.value, ltbItemType2.value)
    End If
End Sub

Private Sub ltbItemName2_Change()
' This sub populates item names and property names on their comboboxes
    Call showCurrentData2
    If ckbExistantProps2.value And ltbItemName2.value <> Empty Then
        ltbPropName2.Clear
        Call populateExistantProps(ltbItemName2.value, ltbPropName2, cmbPropClass2.value)
    End If
End Sub

Private Sub ltbPropName2_Change()
    Call showCurrentData2
End Sub

Private Sub cmbSubArea2_Change()
    If ltbItemType2.value <> Empty Then
        ltbItemName2.Clear
        Call populateItems(ltbItemType2.value, ltbItemName2, cmbSubArea2.value)
    End If
End Sub

Private Sub cmbPropClass2_Change()
    ltbPropName2.Clear
    If ltbItemType2.value <> Empty Then
        If ckbExistantProps2.value And ltbItemName2.value <> Empty Then
            Call populateExistantProps(ltbItemName2.value, ltbPropName2, cmbPropClass2.value)
        Else
            Call populateProps(ltbItemType2.value, ltbPropName2, cmbPropClass2.value)
        End If
    End If
End Sub

' End of the normal property lump of code <Frame 2>
' ####################################################

'#####################################
' Start of the Break Sharing From Code

Private Sub ltbItemTypeBreak_KeyDown(ByVal KeyCode As MSForms.ReturnInteger, ByVal Shift As Integer)
' This sub populates item names and property names on their comboboxes
    If KeyCode = 13 Then                              '13 = Enter / Return
        ltbItemName.Clear
        ltbPropName.Clear
        Call populateItems(ltbItemTypeBreak.value, ltbItemNameBreak)
        Call populateProps(ltbItemTypeBreak.value, ltbPropNameBreak)
    End If
End Sub

Private Sub ltbItemTypeBreak_Click()
' This sub populates item names and property names on their comboboxes
    ltbItemNameOrig.Clear
    ltbPropNameOrig.Clear
    Call populateItems(ltbItemTypeBreak.value, ltbItemNameOrig)
End Sub

Private Sub ltbItemNameOrig_Change()
' This sub populates item names and property names on their comboboxes
    ltbItemNameComp.Clear
    ltbPropNameOrig.Clear
    If ltbItemNameOrig.value <> Empty Then
        Call populateShares(ltbItemNameOrig.value, ltbItemNameComp)
    End If

    If ltbItemNameOrig.value <> Empty Then
        Call populateSharedProps(ltbItemNameOrig.value, ltbPropNameOrig, cmbPropClassBreak.value)
    End If
End Sub

Private Sub ltbPropNameOrig_Change()
' This sub populates item names and property names on their comboboxes
    txbPropNameComp.value = ""
    Call showCurrentShare

    If ltbItemNameOrig.value <> Empty Then
        ltbItemNameComp.Clear
        If ltbPropNameOrig.value <> Empty Then
            Call populateShares(ltbItemNameOrig.value, ltbItemNameComp, ltbPropNameOrig.value)
        Else
            Call populateShares(ltbItemNameOrig.value, ltbItemNameComp)
        End If
    End If
    
    ltbSavedSharesBreak.Clear
    If ltbItemNameComp.value <> Empty And ltbItemNameOrig.value <> Empty Then
        Call populateSavedShares(ltbSavedSharesBreak, getItemTypeFromItemKey(getItemKey(ltbItemNameComp.value)) _
        , getItemTypeFromItemKey(getItemKey(ltbItemNameOrig.value)))
    End If
End Sub

Private Sub ltbItemNameComp_Change()
    txbPropNameComp.value = ""
    Call showCurrentShare
    
    ltbSavedSharesBreak.Clear
    If ltbItemNameComp.value <> Empty And ltbItemNameOrig.value <> Empty Then
        Call populateSavedSharesFromKeys(ltbSavedSharesBreak, getItemTypeFromItemKey(getItemKey(ltbItemNameComp.value)) _
        , getItemTypeFromItemKey(getItemKey(ltbItemNameOrig.value)))
    End If
End Sub

' End of the Break Sharing From Code
'#####################################

'#########
' Auxiliary
Private Sub showCurrentShare()
    Dim itemKey                              As Long
    Dim propKey                              As Long
    Dim valueKey                             As Long
    Dim itemKeyComp                          As Long

    If ltbPropNameOrig.value <> Empty And ltbItemNameComp.value <> Empty Then
        itemKey = getItemKey(ltbItemNameOrig.value)   'itemkey/propkey is the original item/prop pair.
        propKey = getPropKey(ltbPropNameOrig.value)
        itemKeyComp = getItemKey(ltbItemNameComp.value)

        If checkValueExistance(itemKey, propKey) Then
            valueKey = getValueKey(itemKey, propKey)
            On Error Resume Next                      'se não existir o compartilhamento, não quero erro.
            txbPropNameComp.value = getShareName(valueKey, itemKeyComp, itemKey, propKey)
        End If
    Else
        txbPropNameComp.value = ""
    End If
End Sub

Private Sub showCurrentData1()
    Dim propKey                              As Variant         'propKey may receive track or normal type of reference.
    Dim itemKey                              As Long
    Dim unitKey                              As Long
    Dim colDictionary                        As Collection

    txbCurrentValue1.value = ""

    If (ltbPropName1.value <> Empty) And (ltbItemName1.value <> Empty) Then
        propKey = getPropKey(ltbPropName1.value)
        Set colDictionary = createTrackingDictionary

        itemKey = getItemKey(ltbItemName1.value)
        propKey = getPropKey(ltbPropName1.value)

        unitKey = 0
        If getDimKey(CLng(propKey)) <> 0 Then unitKey = 1

        txbCurrentValue1.value = getDataFromAccess(itemKey, CLng(propKey), unitKey, 2, False)    'This "2" makes the unit show up in the value
    End If
End Sub

Private Sub showCurrentData2()
    Dim propKey                              As Variant         'propKey may receive track or normal type of reference.
    Dim itemKey                              As Long
    Dim unitKey                              As Long
    Dim colDictionary                        As Collection

    txbCurrentValue2.value = ""

    If (ltbPropName2.value <> Empty) And (ltbItemName2.value <> Empty) Then
        propKey = getPropKey(ltbPropName2.value)
        Set colDictionary = createTrackingDictionary

        itemKey = getItemKey(ltbItemName2.value)
        propKey = getPropKey(ltbPropName2.value)

        unitKey = 0
        If getDimKey(CLng(propKey)) <> 0 Then unitKey = 1

        txbCurrentValue2.value = getDataFromAccess(itemKey, CLng(propKey), unitKey, 2, False)    'This "2" makes the unit show up in the value
    End If
End Sub

Attribute VB_Name = "helperSubs"
' Chemtech - A Siemens Business ========================================================
'
'=======================================================================================
'Option Explicit
' Desenvolvimento ======================================================================
' <iniciais>            Renan       <email>
' <iniciais>            Paulo       <email>
'=======================================================================================
' Versões ==============================================================================
' v0.5 - Implementação da
' v0.4 - Melhorias gerais e consolidação do CPNM para Excel e Autocad.
'=======================================================================================

Public gCnn                                  As ADODB.Connection
Public gUnitDef                              As unitDefinition
Public Const unitOnlyChar                    As String = "U"
Public Const valueOnlyChar                   As String = "V"
Public Const unitAndValueChar                As String = "D"
Public Const trackingChar                    As String = "Z"
Public Const calcChar                        As String = "C"
Public Const breakString                     As String = "dummy"
Public Const calculatedPropClassKey          As Integer = 5

Public Function isInCollection(col As Collection, key As String) As Boolean
'=======================================================================================
' checa se o argumento "key" aparece na coleção "col", retornando True
'---------------------------------------------------------------------------------------
' [key] chave a ser buscada dentro da coleção
' [col] coleção que deve conter a chave
'---------------------------------------------------------------------------------------
' < Observações >
'---------------------------------------------------------------------------------------
' < Histórico de revisões>
'=======================================================================================
'
    Dim var                                  As Variant
    Dim errNumber                            As Long
    Dim InCollection                         As Boolean

    InCollection = False
    Set var = Nothing

    Err.Clear
    On Error Resume Next
    var = col.Item(key)
    errNumber = CLng(Err.Number)
    On Error GoTo 0

    '5 is not in, 0 and 438 represent incollection
    If errNumber = 5 Then                             ' it is 5 if not in collection
        isInCollection = False
    Else
        isInCollection = True
    End If
End Function

Public Function createTrackingDictionary()
'=======================================================================================
' < descrição da rotina >
'---------------------------------------------------------------------------------------
' < descrição dos argumentos>
'---------------------------------------------------------------------------------------
' < Observações >
'---------------------------------------------------------------------------------------
' < Histórico de revisões>
'=======================================================================================
'
' This function creates a dictionary between field names and the names to display to individual users
    Dim colDictionary                        As Collection

    Set colDictionary = New Collection

    colDictionary.Add "NOME_ITEM", "Nome do item"
    colDictionary.Add "NOME_SUB_ARE", "Sub-area do item"
    colDictionary.Add "NOME_ARE", "Area do item"
    colDictionary.Add "NOME_PLA", "Planta do item"
    colDictionary.Add "NOME_IND", "Industrial do item"
    colDictionary.Add "NOME_UNI", "Unidade de negócio do item"

    colDictionary.Add "Nome do item", "NOME_ITEM"
    colDictionary.Add "Sub-area do item", "NOME_SUB_ARE"
    colDictionary.Add "Area do item", "NOME_ARE"
    colDictionary.Add "Planta do item", "NOME_PLA"
    colDictionary.Add "Industrial do item", "NOME_IND"
    colDictionary.Add "Unidade de negócio do item", "NOME_UNI"

    Set createTrackingDictionary = colDictionary
End Function

Public Sub createGlobalUnitDefinitionObject()
    Set gUnitDef = New unitDefinition
End Sub

Public Function getDbPath()
'=======================================================================================
' < descrição da rotina >
'---------------------------------------------------------------------------------------
' < descrição dos argumentos>
'---------------------------------------------------------------------------------------
' < Observações >
'---------------------------------------------------------------------------------------
' < Histórico de revisões>
'=======================================================================================
'
    Dim strDbPath                            As String

    strDbPath = ActiveDocument.Path & "\teste.mdb"
    If Application.Name = "Microsoft Word" Then
        strDbPath = ActiveDocument.Path & "\teste.mdb"
    ElseIf Application.Name = "Microsoft Excel" Then
        strDbPath = ActiveWorkbook.Path & "\teste.mdb"
    ElseIf Application.Name = "AutoCAD" Then
        strDbPath = ThisDrawing.Path & "\teste.mdb"
    End If

    getDbPath = strDbPath

End Function

Public Function defineDatabaseConnection(Optional promptOption As Integer = 1) As ADODB.Connection
'=======================================================================================
' This sub defines the connection string to the database
'---------------------------------------------------------------------------------------
' [promptOption] : 0, omite o prompt se necessário;
'                : 1, sempre mostra o prompt
'                :-1, ignora o prompt
'---------------------------------------------------------------------------------------
' < Observações >
'---------------------------------------------------------------------------------------
' < Histórico de revisões>
'=======================================================================================
'
    Dim strDbPath                            As String
    Dim strConnect                           As String
    Dim cnn                                  As ADODB.Connection

    Set cnn = New ADODB.Connection

    Select Case promptOption
        Case 1
            strDbPath = getFileDialog

            If strDbPath <> "" Then
                strConnect = "Provider=Microsoft.Jet.OLEDB.4.0;" & _
                             "Data Source=" & strDbPath & ";"
                On Error GoTo 0
                Call storeConnectionString(strConnect)
            End If

        Case 0

            On Error Resume Next
            strConnect = getStoredConnectionString()
            If Err Then
                strDbPath = getFileDialog

                If strDbPath <> "" Then
                    strConnect = "Provider=Microsoft.Jet.OLEDB.4.0;" & _
                                 "Data Source=" & strDbPath & ";"
                    On Error GoTo 0
                    Call storeConnectionString(strConnect)
                End If
            End If
            On Error GoTo 0

        Case -1
            On Error Resume Next
            strConnect = getStoredConnectionString()
            On Error GoTo 0
    End Select

    cnn.ConnectionString = strConnect
    Set defineDatabaseConnection = cnn
End Function

' #############
' Configuration Paths

Public Sub storeConnectionString(storeConnection)
'This sub stores the connection string into Windows registry
    SaveSetting "CPNM", "ConnectionConfig", "ConnectionString", storeConnection
End Sub

Public Function getStoredConnectionString() As String
' This sub stores the connection string into the windows registry
    getStoredConnectionString = GetSetting("CPNM", "ConnectionConfig", "ConnectionString")
End Function

Public Sub storeUnitsXmlPath(xmlPath As String)
'This sub stores the connection string into Windows registry
    SaveSetting "CPNM", "UnitsConfig", "unitsXmlPath", xmlPath
End Sub

Public Function getUnitsXmlPath() As String
' This sub stores the connection string into the windows registry
    getUnitsXmlPath = GetSetting("CPNM", "UnitsConfig", "unitsXmlPath")
End Function

Public Sub storeSharesXmlPath(sharesXmlPath As String)
'This sub stores the connection string into Windows registry
    SaveSetting "CPNM", "SharesConfig", "sharesXmlPath", sharesXmlPath
End Sub

Public Function getSharesXmlPath() As String
' This sub stores the connection string into the windows registry
    getSharesXmlPath = GetSetting("CPNM", "SharesConfig", "sharesXmlPath")
End Function

Public Sub appendToShareXML(itemTypeKey1 As Long, itemTypeKey2 As Long, propList1 As Collection, _
                            propList2 As Collection, strShareName As String)

'=======================================================================================
' Esta rotina salva um compartilhamento definido na interface para o XML.
'---------------------------------------------------------------------------------------
' [itemTypeKey1] - chave primaria do tipo do primeiro item.
' [itemTypeKey2] - chave primaria do tipo do segundo item.
' [propList1]    - colecao de propriedades do primeiro item para compartilhamento.
' [propList2]    - colecao de propriedades do segundo item para compartilhamento.
' [strShareName] - nome a ser dado para o compartilhamento.
'---------------------------------------------------------------------------------------
' a rotina assume que todos os argumentos foram validados antes da chamada.
'---------------------------------------------------------------------------------------
' < Histórico de revisões>
'=======================================================================================
'
    Dim objXml                               As MSXML2.DOMDocument
    Dim objThisNode                          As MSXML2.IXMLDOMNode
    Dim objShareNode                         As MSXML2.IXMLDOMNode
    Dim objPropPairNode                      As MSXML2.IXMLDOMNode

    ' iniciando o documento xml e o nó pai.
    Set objXml = New MSXML2.DOMDocument
    If False = objXml.Load(getSharesXmlPath()) Then     'opening the shared xml path.
        MsgBox "Redefina a localização do xml de configuração dos compartilhamentos"
        storeSharesXmlPath (getFileDialog())
        objXml.Load (getSharesXmlPath())
    End If

    Set objShareNode = objXml.createNode(MSXML2.NODE_ELEMENT, "share", "")

    ' incluindo no nó pai o nome fornecido.
    Set objThisNode = objXml.createNode(MSXML2.NODE_ELEMENT, "name", "")
    objThisNode.Text = strShareName
    Call objShareNode.appendChild(objThisNode)
'#######
    ' including into the parent node the user name who created the share.
    Set objThisNode = objXml.createNode(MSXML2.NODE_ELEMENT, "user", "")
    objThisNode.Text = Environ$("username")
    Call objShareNode.appendChild(objThisNode)
    
    ' including into the parent node the date which the share was created
    Set objThisNode = objXml.createNode(MSXML2.NODE_ELEMENT, "data", "")
    objThisNode.Text = DateTime.Now
    Call objShareNode.appendChild(objThisNode)
'########
    ' including the item types nde into the xml
    Set objThisNode = objXml.createNode(MSXML2.NODE_ELEMENT, "typePair", "")
    Call objShareNode.appendChild(objThisNode)

    ' including the first item type
    Set objThisNode = objXml.createNode(MSXML2.NODE_ELEMENT, "type1", "")
    objThisNode.Text = itemTypeKey1
    Call objShareNode.SelectSingleNode("typePair").appendChild(objThisNode)

    ' including the second item type
    Set objThisNode = objXml.createNode(MSXML2.NODE_ELEMENT, "type2", "")
    objThisNode.Text = itemTypeKey2
    Call objShareNode.SelectSingleNode("typePair").appendChild(objThisNode)

    Set objThisNode = objXml.createNode(MSXML2.NODE_ELEMENT, "propPairSet", "")
    Call objShareNode.appendChild(objThisNode)

    For i = 1 To propList1.Count
        ' creating the propPair node.
        Set objPropPairNode = objXml.createNode(MSXML2.NODE_ELEMENT, "propPair", "")

        ' adding the first prop to the pair node.
        Set objThisNode = objXml.createNode(MSXML2.NODE_ELEMENT, "prop1", "")
        objThisNode.Text = propList1(i)
        Call objPropPairNode.appendChild(objThisNode)

        ' adding the second prop to the pair node
        Set objThisNode = objXml.createNode(MSXML2.NODE_ELEMENT, "prop2", "")
        objThisNode.Text = propList2(i)
        Call objPropPairNode.appendChild(objThisNode)

        ' appending the whole propPair to the propPairSet node.
        Call objShareNode.SelectSingleNode("propPairSet").appendChild(objPropPairNode)
    Next i

    ' Now, the share node is ready to be appended to the whole XML document.
    Call objXml.SelectSingleNode("storedShares").appendChild(objShareNode)
    Call objXml.Save(getSharesXmlPath())
End Sub

Public Sub checkShareCollection(arrCollection As Collection)
'=======================================================================================
' < descrição da rotina >
'---------------------------------------------------------------------------------------
' < descrição dos argumentos>
'---------------------------------------------------------------------------------------
' < Observações >
'---------------------------------------------------------------------------------------
' < Histórico de revisões>
'=======================================================================================
'

'''''FALTA ADICIONAR O TRATAMENTO DE ERRO CORRETO
    Dim propList1                            As Collection
    Dim propList2                            As Collection
    Dim strShareName                         As String
    Dim itemTypeKey1                         As Long
    Dim itemTypeKey2                         As Long
    Dim itemName1                            As String
    Dim itemName2                            As String
    Dim propName1                            As String
    Dim propName2                            As String
    Dim j                                    As Integer
    Dim varArray                             As Variant

    ' initiating propLists
    On Error GoTo checkShareCollection_Error

    Set propList1 = New Collection
    Set propList2 = New Collection

    varArray = arrCollection(1)

    itemName1 = varArray(0)
    itemName2 = varArray(2)

    itemTypeKey1 = getItemTypeFromItemKey(getItemKey(itemName1))
    itemTypeKey2 = getItemTypeFromItemKey(getItemKey(itemName2))

    strShareName = InputBox("Selectione um nome para o compartilhamento")

    For j = 1 To arrCollection.Count
        varArray = arrCollection(j)

        propName1 = varArray(1)
        propName2 = varArray(3)
        
        propList1.Add getPropKey(propName1)
        propList2.Add getPropKey(propName2)

        If itemName1 <> varArray(0) Or itemName2 <> varArray(2) Then
            Err.Raise vbObjectError + 554565, Description:="Para salvar um compartilhamento deve-se adicionar apenas referencias a um par de items."
        End If
    Next j

    Call appendToShareXML(itemTypeKey1, itemTypeKey2, propList1, propList2, strShareName)

    On Error GoTo 0
    GoTo checkShareCollection_ExitSub

checkShareCollection_ExitSub:
    Exit Sub

checkShareCollection_Error:
    errorAction = handleMyError(True)
    Select Case errorAction
        Case -1
            Stop
        Case 1
            Resume Next
        Case 2
            GoTo checkShareCollection_ExitSub
        Case Else
            GoTo checkShareCollection_ExitSub
    End Select

End Sub

Attribute VB_Name = "manipulationSubs"
' Chemtech - A Siemens Business ========================================================
'
'=======================================================================================
Option Explicit
' Desenvolvimento ======================================================================
' <iniciais>            Renan       <email>
'=======================================================================================
' Versões ==============================================================================
'
'
'
'=======================================================================================

Public Sub exportSingleData(strItemName As String, strPropName As String, _
                            strInsertValue As String, strInsertUnit As String, Optional bolAskForConf As Boolean = False)
'=======================================================================================
' < descrição da rotina >
'---------------------------------------------------------------------------------------
' < descrição dos argumentos>
'---------------------------------------------------------------------------------------
' Esta função é um wrapper
'---------------------------------------------------------------------------------------
' < Histórico de revisões>
'=======================================================================================
'
' This sub is done in a way that works only in access!

' Declarations
    Dim rs                         As ADODB.Recordset
    Dim varResponse                As Variant
    Dim itemKey                    As Long
    Dim propKey                As Long
    Dim unitKey                    As Long
    Dim valueExistance             As Boolean
    Dim strCommand                 As String
    Dim idValueJustInserted        As Long
    Dim strConfirmString           As String
    Dim valueKey                   As Long

    itemKey = getItemKey(strItemName)
    propKey = getPropKey(strPropName)
    unitKey = getUnitKey(strPropName, strInsertUnit)

    Call exportSingleDataFromKeys(itemKey, propKey, strInsertValue, unitKey, bolAskForConf)
End Sub

Public Sub exportSingleDataFromKeys(itemKey As Long, propKey As Long, _
                            strInsertValue As String, unitKey As Long, Optional bolAskForConf As Boolean = False)
'=======================================================================================
' < descrição da rotina >
'---------------------------------------------------------------------------------------
' < descrição dos argumentos>
'---------------------------------------------------------------------------------------
' < Observações >
'---------------------------------------------------------------------------------------
' < Histórico de revisões>
'=======================================================================================
'
' This sub is done in a way that works only in access!

' Declarations
    Dim rs                         As ADODB.Recordset
    Dim varResponse                As Variant
    Dim valueExistance             As Boolean
    Dim strCommand                 As String
    Dim idValueJustInserted        As Long
    Dim strConfirmString           As String
    Dim valueKey                   As Long

    On Error GoTo exportSingleData_Error

    ' And i create the recordset to receive some queries
    Set rs = New ADODB.Recordset

    ' Now I trim the value
    strInsertValue = Trim(strInsertValue)
    If unitKey <> 0 Then 'Will convert the value ONLY if there is a unit to convert to.
        strInsertValue = gUnitDef.convertValue(strInsertValue, propKey, unitKey, False)
    End If

    ' Now, we gotta check if the value is already in the database. If it is already there, we have to take a different course of action
    valueExistance = checkValueExistance(itemKey, propKey)

    If valueExistance = False Then
        'Now, we are free to insert the value into the VLUE table
        strCommand = "insert into VALOR_PROPRIEDADES(VALOR_PROP)" & _
                   " values(" & Chr(34) & strInsertValue & Chr(34) & ")"

        ' Executing the thing
        gCnn.Execute (strCommand)

        ' Getting the just inserted value ID
        rs.Open "SELECT @@Identity AS ID", gCnn
        idValueJustInserted = rs.Fields("ID").value

        ' Creating the sql command to INSERT the registry into the LINK table
        strCommand = "insert into LINK_VALORES(ID_ITEM,ID_TIPO_PROP,ID_VALOR) values(" & Chr(34) & itemKey & Chr(34) & "," & Chr(34) & propKey & Chr(34) & "," & Chr(34) & idValueJustInserted & Chr(34) & ")"
        ' Executing the thing =)
Debug.Print strCommand
        gCnn.Execute (strCommand)
    Else

        strConfirmString = "Property " & getPropName(propKey) & " of the item " & getItemName(itemKey) & " already exists" & Chr(10) & _
                           "Are you sure you want to update the old value?"

        ' Checking if the user asked for update confirmation
        If bolAskForConf Then
            varResponse = MsgBox(strConfirmString, vbYesNo, "Confirmation")
        Else
            varResponse = vbYes
        End If

        ' If the update was confirmed, run the things down
        If varResponse = vbYes Then
            ' Getting the Value ID that corresponds to our property-item pair.
            valueKey = getValueKey(itemKey, propKey)

            ' Creating the sql command to UPDATE the registry
            strCommand = "update VALOR_PROPRIEDADES " & _
                       " set VALOR_PROP = " & Chr(34) & strInsertValue & Chr(34) & _
                       " where ID_VALOR = " & valueKey
            ' Executing the thing =)
            gCnn.Execute (strCommand)
        End If
    End If
    On Error GoTo 0

    Exit Sub

exportSingleData_Error:
    Call handleMyError

End Sub

Public Sub changeTrackingData(strItemName, strPropNameTrack, strNewValue)
'=======================================================================================
' < descrição da rotina >
'---------------------------------------------------------------------------------------
' < descrição dos argumentos>
'---------------------------------------------------------------------------------------
' < Observações >
'---------------------------------------------------------------------------------------
' < Histórico de revisões>
'=======================================================================================
'

' Declarations
    Dim rs                         As ADODB.Recordset
    Dim strSQL                     As String
    Dim colDictionary              As Collection
    Dim itemKey                    As Long
    Dim propTrackKey               As String
    Dim bigSelect                  As String


    On Error GoTo changeTrackingData_Error

    ' And i create the recordset to receive some queries
    Set rs = New ADODB.Recordset

    ' getting the dictionary
    Set colDictionary = createTrackingDictionary()

    ' getting the keys
    itemKey = getItemKey(strItemName)
    propTrackKey = colDictionary(strPropNameTrack)

    ' Now, this is the MONSTER QUERY
    bigSelect = "select ITEM.NOME_ITEM, SUB_AREA.NOME_SUB_ARE, AREA.NOME_ARE, PLANTA.NOME_PLA, INDUSTRIAL.NOME_IND, UNIDADE_NEGOCIO.NOME_UNI " & _
              " from UNIDADE_NEGOCIO INNER JOIN ((((INDUSTRIAL INNER JOIN PLANTA ON INDUSTRIAL.ID_IND = PLANTA.ID_IND) INNER JOIN AREA ON " & _
              " PLANTA.ID_PLA = AREA.ID_PLA) INNER JOIN SUB_AREA ON AREA.ID_ARE = SUB_AREA.ID_ARE) INNER JOIN ITEM ON SUB_AREA.ID_SUB_ARE = ITEM.ID_SUB_ARE) ON UNIDADE_NEGOCIO.ID_UNI = INDUSTRIAL.ID_UNI " & _
              " where ITEM.ID_ITEM = " & itemKey

    ' The update command
    strSQL = "update (" & bigSelect & ")" & _
           " set " & propTrackKey & "= " & Chr(34) & strNewValue & Chr(34)

    ' Executing the update command my friend. We are done.
    gCnn.Execute strSQL

    'closing the connection
    On Error GoTo 0

    Exit Sub

changeTrackingData_Error:
    Call handleMyError
End Sub


Public Sub createItem(strItemName As String, strItemType As String, strSubArea As String)
'=======================================================================================
' < descrição da rotina >
'---------------------------------------------------------------------------------------
' < descrição dos argumentos>
'---------------------------------------------------------------------------------------
' < Observações >
'---------------------------------------------------------------------------------------
' < Histórico de revisões>
'=======================================================================================
'
' Declarations
    Dim subAreaKey                 As String
    Dim itemTypeKey                As Long
    Dim itemExistance              As Boolean
    Dim strCommand                 As String
    Dim strConfirmString           As String

    ' Checking if the item already exists
    On Error GoTo createItem_Error
    If checkItemExistance(strItemName) = True Then
        MsgBox "Já existe um Item com este nome cadastrado!"
        Exit Sub
    End If

    ' Here, i get the primary keys
    subAreaKey = getSubAreaKey(strSubArea)
    itemTypeKey = getItemTypeKey(strItemType)
    ' Here i check if the item already exists
    itemExistance = checkItemExistance(strItemName)
    If itemExistance = False Then
        ' Creating the sql command to INSERT the registry
        strCommand = "insert into ITEM(NOME_ITEM,ID_TIPO_ITEM,ID_SUB_ARE) values(" & Chr(34) & strItemName & Chr(34) & "," & itemTypeKey & "," & subAreaKey & ")"
        ' Executing the thing =)
        gCnn.Execute (strCommand)
    Else
        strConfirmString = "Item " & strItemName & "already exists"
    End If
    On Error GoTo 0

    Exit Sub

createItem_Error:
    Call handleMyError

End Sub

Sub createSharing(strItemName1 As String, strPropName1 As String, strItemName2 As String, strPropName2 As String)
'=======================================================================================
' Essa rotina cria o compartilhamento a partir dos nomes dos items e propriedades
'---------------------------------------------------------------------------------------
' [strItemName1] - Nome do primeiro item que entra no compartilhamento
' [strPropName1] - Nome da propriedade do primeiro item para compartilhamento.
' [strItemName2] - Nome do segunda item que entra no compartilhamento
' [strPropName2] - Nome da propriedade do segundo item para compartilhamento.
'---------------------------------------------------------------------------------------
' Essa rotina é um wrapper
'---------------------------------------------------------------------------------------
' < Histórico de revisões>
'=======================================================================================
'
    Dim itemKey1                   As Long
    Dim itemKey2                   As Long
    Dim propKey1                   As Long
    Dim propKey2                   As Long

    itemKey1 = getItemKey(strItemName1)
    propKey1 = getPropKey(strPropName1)
    itemKey2 = getItemKey(strItemName2)
    propKey2 = getPropKey(strPropName2)

    Call createSharingFromKeys(itemKey1, propKey1, itemKey2, propKey2)
End Sub

Sub createSharingFromKeys(itemKey1 As Long, propKey1 As Long, itemKey2 As Long, propKey2 As Long)
'=======================================================================================
' < descrição da rotina >
'---------------------------------------------------------------------------------------
' < descrição dos argumentos>
'---------------------------------------------------------------------------------------
' < Observações >
'---------------------------------------------------------------------------------------
' < Histórico de revisões>
'=======================================================================================
'
    Dim rs                         As New ADODB.Recordset
    Dim strSQL                     As String
    Dim value1Exists               As Boolean
    Dim value2Exists               As Boolean
    Dim valueKey                   As Long
    Dim valueKey4deletion          As Long
    Dim itemKey4creation           As Long
    Dim propKey4creation           As Long
    Dim itemKey4change             As Long
    Dim propKey4change             As Long
    Dim valueKey1                  As Long
    Dim valueKey2                  As Long
    Dim optionLeft                 As Variant

    ' And i create the recordset to receive the query
    On Error GoTo createSharingFromKeys_Error
    Set rs = New ADODB.Recordset

    ' Now, we need to get the values.
    value1Exists = checkValueExistance(itemKey1, propKey1)
    value2Exists = checkValueExistance(itemKey2, propKey2)

    ' setting the keys to -1
    valueKey4deletion = -1
    itemKey4creation = -1
    propKey4creation = -1
    itemKey4change = -1
    propKey4change = -1

    ' Asserting that both properties to be shared have the same dimension
    Call assertDimensionallity(propKey1, propKey2)

    ' Now the cases are going to start
    ' both 1 and 2 dont exist
    If Not value1Exists And Not value2Exists Then 'Here I add a dummy value for the first pair.
        MsgBox "None of the chosen values exists." & vbCr & "I will now create the share with a dummy value"

        Call exportSingleDataFromKeys(itemKey1, propKey1, "Aguardando Upload.", 0, False)
        value1Exists = checkValueExistance(itemKey1, propKey1) 'With this, the system will progress accordingly.
        Exit Sub
    End If

    ' 1 exists, 2 dont
    If value1Exists And Not value2Exists Then
        'now i get the value1 key
        valueKey = getValueKey(itemKey1, propKey1)
        'this is the entry i will link to value1
        itemKey4creation = itemKey2
        propKey4creation = propKey2
    End If

    ' 2 exists, 2 dont
    If Not value1Exists And value2Exists Then
        'now i get the value2 key
        valueKey = getValueKey(itemKey2, propKey2)
        'this is the entry i will link to value2
        itemKey4creation = itemKey1
        propKey4creation = propKey1
    End If

    ' both values exist
    If value1Exists And value2Exists Then

        'now i get the value keys.
        valueKey1 = getValueKey(itemKey1, propKey1)
        valueKey2 = getValueKey(itemKey2, propKey2)

        If valueKey1 <> valueKey2 Then
            ' now, i will delete the second value
            optionLeft = MsgBox("Both values exist! Do you want to keep Value 1?", vbYesNo)

            If optionLeft = vbYes Then
                valueKey = valueKey1                  'this defines the final value key
                valueKey4deletion = getValueKey(itemKey2, propKey2)

                itemKey4change = itemKey2             ' and the link to be changed is the deleted one.
                propKey4change = propKey2
            Else
                valueKey = valueKey2                  'this defines the final value key
                valueKey4deletion = getValueKey(itemKey1, propKey1)    'the other value will be deleted

                itemKey4change = itemKey1             ' and the link to be changed is the deleted one.
                propKey4change = propKey1
            End If

        Else
            'if the keys are equal, it makes no difference which to choose.
            valueKey = valueKey1
            itemKey4change = itemKey2
            propKey4change = propKey2

        End If
    End If

    ' executing the UPDATE statement
    If itemKey4change <> -1 Then
        strSQL = " update LINK_VALORES " & _
               " set ID_VALOR = " & valueKey & _
               " where ID_ITEM = " & itemKey4change & " AND ID_TIPO_PROP = " & propKey4change

        gCnn.Execute (strSQL)
    End If

    ' executing the INSERTION statement
    If itemKey4creation <> -1 Then
        strSQL = " insert into LINK_VALORES(ID_ITEM,ID_TIPO_PROP,ID_VALOR) " & _
               " values (" & itemKey4creation & "," & propKey4creation & "," & valueKey & ")"

        gCnn.Execute (strSQL)
    End If

    ' executing the DELETE statement for the old value
    If valueKey4deletion <> -1 Then
        strSQL = "delete from VALOR_PROPRIEDADES where ID_VALOR = " & valueKey4deletion
        gCnn.Execute (strSQL)
    End If

    On Error GoTo 0

    GoTo createSharingFromKeys_Finally

createSharingFromKeys_Finally:

    Exit Sub

    ' Procedure Error Handler
createSharingFromKeys_Error:
    Dim errorAction                As Integer
    'here goes your specific error handling code.

    ' here comes the generic global error handling code.
    errorAction = handleMyError()
    Select Case errorAction
        Case -1
Stop
        Case 1
            Resume Next
        Case 2
            GoTo createSharingFromKeys_Finally
        Case Else
Stop
    End Select
End Sub

Sub breakSharing(strItemName1 As String, strPropName1 As String, strItemName2 As String, strPropName2 As String)
'=======================================================================================
' < descrição da rotina >
'---------------------------------------------------------------------------------------
' < descrição dos argumentos>
'---------------------------------------------------------------------------------------
' < Observações >
'---------------------------------------------------------------------------------------
' < Histórico de revisões>
'=======================================================================================
'
' Declarations
    Dim rs                         As New ADODB.Recordset
    Dim strSQL                     As String
    Dim itemKey1                   As Long
    Dim itemKey2                   As Long
    Dim propKey1                   As Long
    Dim propKey2                   As Long
    Dim dimKey1                    As Long
    Dim dimKey2                    As Long
    Dim valueKey                   As Long
    Dim valueShared                As String
    Dim idValueJustInserted        As Long


    ' And i create the recordset to receive the query
    Set rs = New ADODB.Recordset

    '####
    ' First, we need to get the keys.
    itemKey1 = getItemKey(strItemName1)
    propKey1 = getPropKey(strPropName1)
    itemKey2 = getItemKey(strItemName2)
    propKey2 = getPropKey(strPropName2)

    ' We now get the value of the property
    valueKey = getValueKey(itemKey1, propKey1)
    valueShared = getValue(valueKey)

    ' inserting the new copy of the value
    strSQL = "insert into VALOR_PROPRIEDADES (VALOR_PROP)" & _
           " values (" & Chr(34) & valueShared & Chr(34) & ")"

    ' executing the command
    gCnn.Execute (strSQL)

    ' Now I need to get the key of the new inserted values
    rs.Open "SELECT @@Identity AS ID", gCnn
    idValueJustInserted = rs.Fields("ID").value

    ' now, we have to change the break the old references.
    strSQL = "update LINK_VALORES " & _
           " set ID_VALOR = " & idValueJustInserted & _
           " where ID_ITEM = " & itemKey2 & " AND ID_TIPO_PROP = " & propKey2

    ' and now I execute the new value
    gCnn.Execute (strSQL)

    If Err Then
        MsgBox "Houve erro na quebra do compartilhamento"
    End If

End Sub

Public Sub assertDimensionallity(propKey1 As Long, propKey2 As Long)
    Dim dimKey1                    As Long
    Dim dimKey2                    As Long

    dimKey1 = getDimKey(propKey1)
    dimKey2 = getDimKey(propKey2)

    If dimKey1 <> dimKey2 Then
        Err.Raise 175645 + vbObjectError, Description:="You are trying to share values which do not agree dimensionally"
    End If
End Sub

Attribute VB_Name = "obTimer"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'How many times per second is the counter updated?
Private Declare Function QueryFrequency Lib "kernel32" _
                                        Alias "QueryPerformanceFrequency" ( _
                                        lpFrequency As Currency) As Long

'What is the counter's value
Private Declare Function QueryCounter Lib "kernel32" _
                                      Alias "QueryPerformanceCounter" ( _
                                      lpPerformanceCount As Currency) As Long

'Variables to store the counter information
Dim mcyFrequency                             As Currency
Dim mcyOverhead                              As Currency
Dim mcyStarted                               As Currency
Dim mcyStopped                               As Currency

Private Sub class_initialize()
    Dim cyCount1 As Currency, cyCount2       As Currency

    'Get the counter frequency
    QueryFrequency mcyFrequency

    'Call the hi-res counter twice, to check how long it takes
    QueryCounter cyCount1
    QueryCounter cyCount2

    'Store the call overhead
    mcyOverhead = cyCount2 - cyCount1
End Sub


Public Sub StartTimer()
'Get the time that you started
    QueryCounter mcyStarted
End Sub

Public Sub StopTimer()
'Get the time that you stopped
    QueryCounter mcyStopped
End Sub

Public Property Get Elapsed() As Double
    Dim cyTimer                              As Currency

    'Have you stopped or not?
    If mcyStopped = 0 Then
        QueryCounter cyTimer
    Else
        cyTimer = mcyStopped
    End If

    'If you have a frequency, return the duration, in seconds
    If mcyFrequency > 0 Then
        Elapsed = (cyTimer - mcyStarted - mcyOverhead) / mcyFrequency
    End If
End Property

Attribute VB_Name = "querySubs"
' Chemtech - A Siemens Business ========================================================
'
'=======================================================================================
Option Explicit
' Desenvolvimento ======================================================================
' <iniciais>            Renan       <email>
'=======================================================================================
' Versões ==============================================================================
'
'
'
'=======================================================================================

Public Function getItemTypeKey(strItemTypeName) As Long
'=======================================================================================
' < descrição da rotina >
'---------------------------------------------------------------------------------------
' < descrição dos argumentos>
'---------------------------------------------------------------------------------------
' < Observações >
'---------------------------------------------------------------------------------------
' < Histórico de revisões>
'=======================================================================================
'
' The following code populates the comboboxes with item's names and prop's names

' Declarations
    Dim rs                                   As ADODB.Recordset
    Dim strSQL                               As String

    ' And i create the recordset to receive the query
    Set rs = New ADODB.Recordset

    ' Getting the item type primary key from query
    strSQL = "Select ID_TIPO_ITEM from TIPO_ITEM where NOME_TIPO_ITEM = " & Chr(34) & strItemTypeName & Chr(34)
    rs.Open strSQL, gCnn

    ' Checking if something weird just happenned
    Call checkKeyness(rs)

    ' Checking if there is a problem
    getItemTypeKey = rs.Fields("ID_TIPO_ITEM").value

End Function

Public Function getItemKey(strItemName) As Long
'=======================================================================================
' < descrição da rotina >
'---------------------------------------------------------------------------------------
' < descrição dos argumentos>
'---------------------------------------------------------------------------------------
' < Observações >
'---------------------------------------------------------------------------------------
' < Histórico de revisões>
'=======================================================================================
'
' Declarations
    Dim rs                                   As ADODB.Recordset
    Dim strSQL                               As String

    ' And i create the recordset to receive the query
    Set rs = New ADODB.Recordset

    ' Query string for the value
    strSQL = "select ID_ITEM from ITEM where NOME_ITEM = " & Chr(34) & strItemName & Chr(34)

    ' getting the query into rs
    rs.Open strSQL, gCnn

    ' getting to know if the query returned stuff
    Call checkKeyness(rs)

    ' If register is found, get the keys.
    getItemKey = rs.Fields("ID_ITEM")

End Function

Public Function getItemTypeFromItemKey(itemKey As Long) As Long
'=======================================================================================
' < descrição da rotina >
'---------------------------------------------------------------------------------------
' < descrição dos argumentos>
'---------------------------------------------------------------------------------------
' < Observações >
'---------------------------------------------------------------------------------------
' < Histórico de revisões>
'=======================================================================================
'
' Declarations
    Dim rs                                   As ADODB.Recordset
    Dim strSQL                               As String

    ' And i create the recordset to receive the query
    Set rs = New ADODB.Recordset

    ' Query string for the value
    strSQL = "select ID_TIPO_ITEM from ITEM where ID_ITEM = " & itemKey

    ' getting the query into rs
    rs.Open strSQL, gCnn

    ' getting to know if the query returned stuff
    Call checkKeyness(rs)

    ' If register is found, get the keys.
    getItemTypeFromItemKey = rs.Fields("ID_TIPO_ITEM").value

End Function

Public Function getPropKey(strPropName As String) As Long
'=======================================================================================
' < descrição da rotina >
'---------------------------------------------------------------------------------------
' < descrição dos argumentos>
'---------------------------------------------------------------------------------------
' < Observações >
'---------------------------------------------------------------------------------------
' < Histórico de revisões>
'=======================================================================================
'
    Dim rs                                   As ADODB.Recordset
    Dim strSQL                               As String

    ' And i create the recordset to receive the query
    Set rs = New ADODB.Recordset

    ' Query string for the value
    strSQL = "select ID_TIPO_PROP from TIPO_PROPRIEDADES where NOME_TIPO_PROP = " & Chr(34) & strPropName & Chr(34)

    ' getting the query into rs
    rs.Open strSQL, gCnn

    ' getting to know if the query returned stuff
    Call checkKeyness(rs)

    ' If register is found, get the key.
    getPropKey = rs.Fields("ID_TIPO_PROP")

End Function

Public Function getDimKey(propKey As Long) As Long
'=======================================================================================
' < descrição da rotina >
'---------------------------------------------------------------------------------------
' < descrição dos argumentos>
'---------------------------------------------------------------------------------------
' < Observações >
'---------------------------------------------------------------------------------------
' < Histórico de revisões>
'=======================================================================================
'
    Dim rs                                   As ADODB.Recordset
    Dim strSQL                               As String

    Set rs = New ADODB.Recordset

    strSQL = "select ID_DIMENSAO, NOME_TIPO_PROP from TIPO_PROPRIEDADES where ID_TIPO_PROP = " & propKey

    rs.Open strSQL, gCnn

    Call checkKeyness(rs)

    If Not IsNull(rs.Fields("ID_DIMENSAO").value) Then
        getDimKey = rs.Fields("ID_DIMENSAO").value
    Else
        getDimKey = 0
    End If
End Function

Public Function getSubAreaKey(strSubAreaName As String) As Long
'=======================================================================================
' < descrição da rotina >
'---------------------------------------------------------------------------------------
' < descrição dos argumentos>
'---------------------------------------------------------------------------------------
' < Observações >
'---------------------------------------------------------------------------------------
' < Histórico de revisões>
'=======================================================================================
'
    Dim rs                                   As ADODB.Recordset
    Dim strSQL                               As String

    ' And i create the recordset to receive the query
    Set rs = New ADODB.Recordset

    ' Query string for the value
    strSQL = "select ID_SUB_ARE from SUB_AREA where NOME_SUB_ARE = " & Chr(34) & strSubAreaName & Chr(34)

    ' getting the query into rs
    rs.Open strSQL, gCnn

    ' getting to know if the query returned stuff
    Call checkKeyness(rs)

    ' If register is found, get the key.
    getSubAreaKey = rs.Fields("ID_SUB_ARE").value

End Function

Public Function getSubAreaKeyFromItemKey(itemKey As Long) As Long
'=======================================================================================
' < descrição da rotina >
'---------------------------------------------------------------------------------------
' < descrição dos argumentos>
'---------------------------------------------------------------------------------------
' < Observações >
'---------------------------------------------------------------------------------------
' < Histórico de revisões>
'=======================================================================================
'
' Declarations
    Dim rs                                   As ADODB.Recordset
    Dim strSQL                               As String

    ' And i create the recordset to receive the query
    Set rs = New ADODB.Recordset

    ' Query string for the value
    strSQL = "select ID_SUB_ARE from ITEM where ID_ITEM = " & itemKey

    ' getting the query into rs
    rs.Open strSQL, gCnn

    ' getting to know if the query returned stuff
    Call checkKeyness(rs)

    ' If register is found, get the key.
    getSubAreaKeyFromItemKey = rs.Fields("ID_SUB_ARE").value

End Function

Public Function getPropClassKey(strPropClass As String) As Long
'=======================================================================================
' < descrição da rotina >
'---------------------------------------------------------------------------------------
' < descrição dos argumentos>
'---------------------------------------------------------------------------------------
' < Observações >
'---------------------------------------------------------------------------------------
' < Histórico de revisões>
'=======================================================================================
'
' Declarations
    Dim rs                                   As ADODB.Recordset
    Dim strSQL                               As String

    ' And i create the recordset to receive the query
    Set rs = New ADODB.Recordset

    ' Query string for the value
    strSQL = "select ID_CLASSE_TIPO_PROP from CLASSE_TIPO_PROP where NOME_CLASSE_TIPO_PROP = " & Chr(34) & strPropClass & Chr(34)

    ' getting the query into rs
    rs.Open strSQL, gCnn

    ' getting to know if the query returned stuff
    Call checkKeyness(rs)

    ' If register is found, get the key.
    getPropClassKey = rs.Fields("ID_CLASSE_TIPO_PROP").value

End Function

Public Function getItemName(itemKey As Long) As String
'=======================================================================================
' < descrição da rotina >
'---------------------------------------------------------------------------------------
' < descrição dos argumentos>
'---------------------------------------------------------------------------------------
' < Observações >
'---------------------------------------------------------------------------------------
' < Histórico de revisões>
'=======================================================================================
'
' Declarations
    Dim rs                                   As ADODB.Recordset
    Dim strSQL                               As String

    ' And i create the recordset to receive the query
    Set rs = New ADODB.Recordset

    ' Query string for the value
    strSQL = "select NOME_ITEM from ITEM where ID_ITEM = " & itemKey

    ' getting the query into rs
    rs.Open strSQL, gCnn

    ' getting to know if the query returned stuff
    Call checkKeyness(rs)

    ' If register is found, get the name.
    getItemName = rs.Fields("NOME_ITEM")

End Function

Public Function getItemClassKeyFromItemKey(itemKey As Long) As String
'=======================================================================================
' < descrição da rotina >
'---------------------------------------------------------------------------------------
' < descrição dos argumentos>
'---------------------------------------------------------------------------------------
' < Observações >
'---------------------------------------------------------------------------------------
' < Histórico de revisões>
'=======================================================================================
'
' Declarations
    Dim rs                                   As ADODB.Recordset
    Dim strSQL                               As String
    Dim itemTypeKey                          As Long

    ' And i create the recordset to receive the query
    Set rs = New ADODB.Recordset

    itemTypeKey = getItemTypeFromItemKey(itemKey)

    ' Query string for the value
    strSQL = "select ID_CLASSE_TIPO_ITEM from TIPO_ITEM where ID_TIPO_ITEM = " & itemTypeKey

    ' getting the query into rs
    rs.Open strSQL, gCnn

    ' getting to know if the query returned stuff
    Call checkKeyness(rs)

    ' If register is found, get the name.
    getItemClassKeyFromItemKey = rs.Fields("ID_CLASSE_TIPO_ITEM")

End Function

Public Function getItemClassKey(strItemClassName As String) As Long
'=======================================================================================
' < descrição da rotina >
'---------------------------------------------------------------------------------------
' < descrição dos argumentos>
'---------------------------------------------------------------------------------------
' < Observações >
'---------------------------------------------------------------------------------------
' < Histórico de revisões>
'=======================================================================================
'
' Declarations
    Dim rs                                   As ADODB.Recordset
    Dim strSQL                               As String

    ' And i create the recordset to receive the query
    Set rs = New ADODB.Recordset

    ' Query string for the value
    strSQL = "select ID_CLASSE_TIPO_ITEM from CLASSE_TIPO_ITEM where NOME_CLASSE_TIPO_ITEM = " & Chr(34) & strItemClassName & Chr(34)

    ' getting the query into rs
    rs.Open strSQL, gCnn

    ' getting to know if the query returned stuff
    Call checkKeyness(rs)

    ' If register is found, get the key.
    getItemClassKey = rs.Fields("ID_CLASSE_TIPO_ITEM").value

End Function

Public Function getValueKey(itemKey, propKey) As Long
'=======================================================================================
' < descrição da rotina >
'---------------------------------------------------------------------------------------
' < descrição dos argumentos>
'---------------------------------------------------------------------------------------
' < Observações >
'---------------------------------------------------------------------------------------
' < Histórico de revisões>
'=======================================================================================
'
' Declarations
    Dim rs                                   As ADODB.Recordset
    Dim strSQL                               As String

    ' Aqui entra o comando em SQL para fazer a query
    strSQL = " SELECT ID_VALOR " & _
             " FROM LINK_VALORES WHERE ID_ITEM = " & itemKey & " And ID_TIPO_PROP = " & propKey

    ' Criando um recordset com o resultado da query
    Set rs = New ADODB.Recordset
    rs.CursorLocation = adUseClient
    rs.Open strSQL, gCnn

    Call checkKeyness(rs)

    ' Returning the value
    getValueKey = rs.Fields("ID_VALOR").value

End Function

Public Function getPropName(propKey) As String
'=======================================================================================
' < descrição da rotina >
'---------------------------------------------------------------------------------------
' < descrição dos argumentos>
'---------------------------------------------------------------------------------------
' < Observações >
'---------------------------------------------------------------------------------------
' < Histórico de revisões>
'=======================================================================================
'
' Declarations
    Dim rs                                   As ADODB.Recordset
    Dim strSQL                               As String

    ' And i create the recordset to receive the query
    Set rs = New ADODB.Recordset

    ' Query string for the value
    strSQL = "select NOME_TIPO_PROP from TIPO_PROPRIEDADES where ID_TIPO_PROP = " & propKey

    ' getting the query into rs
    rs.Open strSQL, gCnn

    ' getting to know if the query returned stuff
    Call checkKeyness(rs)

    ' If register is found, get the name.
    getPropName = rs.Fields("NOME_TIPO_PROP")

End Function

Public Function getShareName(valueKey As Long, itemKeyComp As Long, _
                             itemKeyOrig As Long, propKeyOrig As Long) As String
'=======================================================================================
' < descrição da rotina >
'---------------------------------------------------------------------------------------
' < descrição dos argumentos>
'---------------------------------------------------------------------------------------
' < Observações >
'---------------------------------------------------------------------------------------
' < Histórico de revisões>
'=======================================================================================
'
' Declarations
    Dim rs                                   As ADODB.Recordset
    Dim strSQL                               As String

    ' And i create the recordset to receive the query
    Set rs = New ADODB.Recordset
    rs.CursorLocation = adUseClient

    ' Query string for the value
    strSQL = "select NOME_TIPO_PROP from TIPO_PROPRIEDADES inner join LINK_VALORES on TIPO_PROPRIEDADES.ID_TIPO_PROP = LINK_VALORES.ID_TIPO_PROP" & _
             " where LINK_VALORES.ID_VALOR = " & valueKey & " and LINK_VALORES.ID_ITEM = " & itemKeyComp & _
             " and NOT(LINK_VALORES.ID_TIPO_PROP = " & propKeyOrig & " and LINK_VALORES.ID_ITEM = " & itemKeyOrig & ")"
    ' getting the query into rs
    rs.Open strSQL, gCnn

    ' getting to know if the query returned stuff
    Call checkKeyness(rs)

    ' If register is found, get the name.
    getShareName = rs.Fields("NOME_TIPO_PROP")
End Function

Public Function getUnitKey(strPropName As String, strUnitName As String) As Long
'=======================================================================================
' Retorna a chave da unidade a partir do seu simbolo e nome de propriedade
' Esta função é um wrapper.
'---------------------------------------------------------------------------------------
' [strPropName] nome da propriedade, conforme definido no database
' [strUnitName] nome/simbolo da unidade. E.g. Pa, kgf/cm², °C.
'---------------------------------------------------------------------------------------
' Essa rotina confia na implementação das classes "unit" e "unitDefinition".
' Deve existir uma instancia global gUnitDef de unitDefinition que define todas as units.
' A classe "unitDefinition" depende de um arquivo XML para a definição dos objetos unit.
'---------------------------------------------------------------------------------------
' < Histórico de revisões>
'=======================================================================================
'
    getUnitKey = gUnitDef.getUnitKey(strPropName, strUnitName)
End Function

Public Function getUnitSymbol(propKey As Long, unitKey As Long) As Long
'=======================================================================================
' Retorna o simbolo da unidade a partir da chave da propriedade e chave da unidade
' Esta função é um wrapper.
'---------------------------------------------------------------------------------------
' [propKey] chave da propriedade conforme definida no database
' [unitKey] chave da unidade conforme definida no XML
'---------------------------------------------------------------------------------------
' Essa rotina confia na implementação das classes "unit" e "unitDefinition".
' Deve existir uma instancia global gUnitDef de unitDefinition que define todas as units.
' A classe "unitDefinition" depende de um arquivo XML para a definição dos objetos unit.
'---------------------------------------------------------------------------------------
' < Histórico de revisões>
'=======================================================================================
'
    getUnitSymbol = gUnitDef.getUnitSymbol(propKey, unitKey)
End Function

Public Function getValue(valueKey) As String
'=======================================================================================
' < descrição da rotina >
'---------------------------------------------------------------------------------------
' < descrição dos argumentos>
'---------------------------------------------------------------------------------------
' < Observações >
'---------------------------------------------------------------------------------------
' < Histórico de revisões>
'=======================================================================================
'
' Declarations
    Dim rs                                   As ADODB.Recordset
    Dim strSQL                               As String

    ' And i create the recordset to receive the query
    Set rs = New ADODB.Recordset

    ' Query string for the value
    strSQL = "select VALOR_PROP from VALOR_PROPRIEDADES where ID_VALOR = " & valueKey

    ' getting the query into rs
    rs.Open strSQL, gCnn

    ' If register is found, get the name.
    getValue = rs.Fields("VALOR_PROP")
End Function

Public Function checkItemExistance(strItemName As String) As Boolean
'=======================================================================================
' < descrição da rotina >
'---------------------------------------------------------------------------------------
' < descrição dos argumentos>
'---------------------------------------------------------------------------------------
' < Observações >
'---------------------------------------------------------------------------------------
' < Histórico de revisões>
'=======================================================================================
'
' This sub checks for the existence of itemKey and propTypeKey in the "VALOR_PROPRIEDADES" table

' Declarations
    Dim rs                                   As ADODB.Recordset
    Dim strSQL                               As String


    ' now I check if the value already exists
    strSQL = "select ID_ITEM from ITEM " & _
             " where NOME_ITEM = " & Chr(34) & strItemName & Chr(34)

    ' now I open this check query;
    Set rs = New ADODB.Recordset
    rs.Open strSQL, gCnn

    ' If the query is empty, means the value is not yet there.
    If rs.EOF Then
        checkItemExistance = False
    Else
        checkItemExistance = True
    End If

End Function

Public Function checkValueExistance(itemKey As Long, propKey As Long) As Boolean
'=======================================================================================
' < descrição da rotina >
'---------------------------------------------------------------------------------------
' < descrição dos argumentos>
'---------------------------------------------------------------------------------------
' This sub checks for the existence of itemKey and propTypeKey in the "VALOR_PROPRIEDADES" table
'---------------------------------------------------------------------------------------
' < Histórico de revisões>
'=======================================================================================
'
    Dim valueKey                             As Long

    On Error Resume Next
    valueKey = getValueKey(itemKey, propKey)

    If Err = 0 Then
        checkValueExistance = True
    Else
        checkValueExistance = False
    End If
End Function

Public Function checkIfIsCalc(propKey As Long) As Boolean

    Dim strSQL                               As String
    Dim rs                                   As ADODB.Recordset

    Set rs = New ADODB.Recordset
    rs.CursorLocation = adUseClient

    ' agora eu preciso verificar se a propriedade é comum, ou é calculada.
    strSQL = "select ID_TIPO_PROP from TIPO_PROPRIEDADES where ID_CLASSE_TIPO_PROP = " & calculatedPropClassKey & " AND ID_TIPO_PROP = " & CLng(propKey)
    rs.Open strSQL, gCnn
    Select Case rs.RecordCount
        Case 1
            checkIfIsCalc = True
        Case 0
            checkIfIsCalc = False
        Case Else
            Err.Raise vbObjectError + 112525, Description:="OMFG YOU GOT A KEYNESS PROBLEM!!!"
    End Select
End Function

Public Function checkIfIsShared(itemKey As Long, propKey As Long)
'=======================================================================================
' < descrição da rotina >
'---------------------------------------------------------------------------------------
' < descrição dos argumentos>
'---------------------------------------------------------------------------------------
' < Observações >
'---------------------------------------------------------------------------------------
' < Histórico de revisões>
'=======================================================================================
'
' The following code populates the item type combobox with item_type's name

' Declarations
    Dim rs                                   As ADODB.Recordset
    Dim strSQL                               As String
    Dim valueKey                             As Long

    On Error GoTo checkIfIsShared_Error

    ' And i create the recordset to receive the query
    Set rs = New ADODB.Recordset
    rs.CursorLocation = adUseClient

    ' getting the valueKey of the pair
    valueKey = getValueKey(itemKey, propKey)

    ' Here i put the command for the query
    strSQL = "select ID_ITEM from LINK_VALORES where ID_VALOR = " & valueKey

    ' Here i open the query in the recordset rs
    rs.Open strSQL, gCnn

    ' Returning the result
    If rs.RecordCount > 1 Then
        checkIfIsShared = True
    Else
        checkIfIsShared = False
    End If

    On Error GoTo 0

    Exit Function

checkIfIsShared_Error:
    'getValueKey will raise this error if no value is found. Which means the value does not exist, so, can't be shared.
    If Err.Number = 100000 + vbObjectError Then
        Resume Next
    Else
        Call handleMyError
    End If
End Function

Attribute VB_Name = "shareQueue"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Dim shareCount                               As Long
Dim queue(1000, 3)                           As Variant

Private Sub class_initialize()
    shareCount = 0
End Sub

Public Property Get countShares()
    countShares = shareCount
End Property

Public Sub dequeue(index As Integer)
    Dim j                                    As Integer

    For j = 0 To 3
        queue(index, j) = queue(shareCount - 1, j)
    Next j

    shareCount = shareCount - 1
End Sub

Public Property Get sharesCollection() As Collection
    Dim i                                    As Long
    Dim tempArray(3)                         As Variant

    Set sharesCollection = New Collection

    For i = 0 To shareCount - 1
        tempArray(0) = queue(i, 0)
        tempArray(1) = queue(i, 1)
        tempArray(2) = queue(i, 2)
        tempArray(3) = queue(i, 3)

        sharesCollection.Add tempArray
    Next i
End Property

Public Sub Clear()
    shareCount = 0
End Sub

Public Sub enqueue(strItemName1 As String, strPropName1 As String, strItemName2 As String, strPropName2 As String)
    queue(shareCount, 0) = strItemName1
    queue(shareCount, 1) = strPropName1
    queue(shareCount, 2) = strItemName2
    queue(shareCount, 3) = strPropName2

    shareCount = shareCount + 1
End Sub

Attribute VB_Name = "unit"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Public dimension                             As Integer
Public key                                   As Long
Public convFactor                            As Double
Public convOffset                            As Double
Public symbol                                As String

Attribute VB_Name = "unitDefinition"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Public pUnitCollection                       As Collection

Private Sub class_initialize()
    Set Me.pUnitCollection = getUnitsCollectionFromXML
End Sub

Public Function convertValue(strValue As String, propKey As Long, _
                             unitKey As Long, bolImporting As Boolean) As String
'=======================================================================================
' conversão de um valor de ou para o SI.
'---------------------------------------------------------------------------------------
' [valueSI] - Se TRUE, converte strValue do SI para a unidade dada em unitKey (import)
'           - Se FALSE, converte strValue da unidade dada em unitKey para o SI (export)
'---------------------------------------------------------------------------------------
' A conversão funciona da seguinte forma.
'           offsetFactor + (convFactor * <nãoSI>) = <SI>
'---------------------------------------------------------------------------------------
' < Histórico de revisões>
'=======================================================================================
'
'#############################
' Há um problema conhecido.
' Esse método Só vai funcionar corretamente se o separador de decimal do seu sistema for a virgula. (padrão br)
'#############################

    Dim convFactor                           As Double
    Dim offsetFactor                         As Double
    Dim dimKey                               As Long
    Dim convertedValue                       As Variant
    Dim dblValue                             As Double
    Dim unitSymbol                           As String

    On Error GoTo convertValue_Error
    ' getting the dimension key
    dimKey = getDimKey(propKey)

    If unitKey <> 0 And dimKey <> 0 Then
        ' with the dimension key, i get the dictionary with the conversion factors.

        convFactor = getConvFactor(propKey, unitKey)
        offsetFactor = getOffsetFactor(propKey, unitKey)

        dblValue = CDbl(strValue)
        unitSymbol = getUnitSymbol(propKey, unitKey)

        If bolImporting Then    'So, dblValue is IN SI.
            convertedValue = (dblValue - offsetFactor) / convFactor
        Else    'So, dblValue is NOT IN SI
            convertedValue = dblValue * convFactor + offsetFactor
        End If
    Else
        convertedValue = strValue
    End If

    convertValue = Format(CStr(convertedValue), "standard")

    On Error GoTo 0

    GoTo convertValue_Finally

convertValue_Finally:

    Exit Function

    ' Procedure Error Handler
convertValue_Error:
    Dim errorAction                          As Integer
    'here goes your specific error handling code.

    ' here comes the generic global error handling code.
    errorAction = handleMyError()
    Select Case errorAction
        Case -1
            Stop
        Case 1
            Resume Next
        Case 2
            GoTo convertValue_Finally
        Case Else
            Stop
    End Select
End Function

Public Property Get getUnitKey(strPropName As String, strUnitSymbol As String) As Long
    Dim tempUnit                             As unit
    Dim propKey                              As Long
    Dim dimKey                               As Long

    propKey = getPropKey(strPropName)
    dimKey = getDimKey(propKey)

    If dimKey <> 0 And strUnitSymbol <> "" Then
        For Each tempUnit In Me.pUnitCollection
            If tempUnit.symbol = strUnitSymbol And tempUnit.dimension = dimKey Then

                getUnitKey = tempUnit.key
                Exit Property

            End If
        Next tempUnit
    Else
        getUnitKey = 0
    End If
End Property

Private Function getConvFactor(propKey As Long, unitKey As Long) As Double
    Dim tempUnit                             As unit

    If unitKey <> 0 Then
        Set tempUnit = getUnitObjectFromKeys(propKey, unitKey)
        If Not tempUnit Is Nothing Then getConvFactor = tempUnit.convFactor
    Else
        getConvFactor = 1
    End If
End Function

Private Function getOffsetFactor(propKey As Long, unitKey As Long) As Double
    Dim tempUnit                             As unit

    If unitKey <> 0 Then
        Set tempUnit = getUnitObjectFromKeys(propKey, unitKey)
        If Not tempUnit Is Nothing Then getOffsetFactor = tempUnit.convOffset
    Else
        getOffsetFactor = 0
    End If
End Function

Public Property Get getUnitSymbol(propKey As Long, unitKey As Long) As String
    Dim tempUnit                             As unit

    If unitKey <> 0 Then
        Set tempUnit = getUnitObjectFromKeys(propKey, unitKey)
        If Not tempUnit Is Nothing Then getUnitSymbol = tempUnit.symbol
    Else
        getUnitSymbol = ""
    End If
End Property

'##########
' Privates

Private Function getUnitObjectFromKeys(propKey As Long, unitKey As Long) As unit
    Dim dimKey                               As Long
    Dim tempUnit                             As unit
    Dim strUnitAddress                       As String

    dimKey = getDimKey(propKey)

    strUnitAddress = dimKey & "|" & unitKey

    '    If isInCollection(Me.pUnitCollection, strUnitAddress) Then
    Set tempUnit = Me.pUnitCollection(strUnitAddress)
    Set getUnitObjectFromKeys = tempUnit
    '    End If
End Function

Private Function getUnitsCollectionFromXML() As Collection

    Dim objXml           As MSXML2.DOMDocument
    Dim unitList         As MSXML2.IXMLDOMNodeList
    Dim unit             As MSXML2.IXMLDOMElement
    Dim itemIndex        As Integer
    Dim tempUnit         As unit
    Dim unitCol          As Collection

    Set objXml = New MSXML2.DOMDocument

    If False = objXml.Load(getUnitsXmlPath()) Then
        MsgBox "Redefina a localização do xml de configuração do sistema de unidades"
        storeUnitsXmlPath (getFileDialog())
        objXml.Load (getUnitsXmlPath())
    End If

    Set unitList = objXml.getElementsByTagName("unit")

    'unitList.item.Attributes

    Set unitCol = New Collection

    For itemIndex = 0 To unitList.Length - 1
        Set tempUnit = New unit

        tempUnit.symbol = CStr(unitList.Item(itemIndex).SelectSingleNode("symbol").Text)
        tempUnit.convFactor = CDbl(unitList.Item(itemIndex).SelectSingleNode("convFactor").Text)
        tempUnit.convOffset = CDbl(unitList.Item(itemIndex).SelectSingleNode("convOffset").Text)
        tempUnit.dimension = CInt(unitList.Item(itemIndex).SelectSingleNode("dimension").Text)
        tempUnit.key = CLng(unitList.Item(itemIndex).SelectSingleNode("key").Text)

        unitCol.Add Item:=tempUnit, key:=tempUnit.dimension & "|" & tempUnit.key

    Next itemIndex

    Set getUnitsCollectionFromXML = unitCol
End Function

Attribute VB_Name = "userFormSubs"
' Chemtech - A Siemens Business ========================================================
'
'=======================================================================================
'Option Explicit
' Desenvolvimento ======================================================================
' <iniciais>            Renan       <email>
'=======================================================================================
' Versões ==============================================================================
'
'
'
'=======================================================================================

Sub runCPNM()
'=======================================================================================
' < descrição da rotina >
'---------------------------------------------------------------------------------------
' < descrição dos argumentos>
'---------------------------------------------------------------------------------------
' < Observações >
'---------------------------------------------------------------------------------------
' < Histórico de revisões>
'=======================================================================================
'
' This sub runs the information manager
    frmRunManager.Show
End Sub

Public Sub populateItems(strItemTypeName As String, cmbItemName, Optional strSubAreaName As String)
'=======================================================================================
' < descrição da rotina >
'---------------------------------------------------------------------------------------
' < descrição dos argumentos>
'---------------------------------------------------------------------------------------
' < Observações >
'---------------------------------------------------------------------------------------
' < Histórico de revisões>
'=======================================================================================
'
' The following code populates the comboboxes with item's names and prop's names

' Declarations
    Dim rs                                   As ADODB.Recordset
    Dim itemTypeKey                          As Long
    Dim strSQL                               As String
    Dim subAreaKey                           As Long

    On Error GoTo populateItems_Error

    ' And i create the recordset to receive the query
    Set rs = New ADODB.Recordset

    ' POPULATING THE ITEM COMBOBOX
    itemTypeKey = getItemTypeKey(strItemTypeName)

    ' Now, I query over all item's where item.itemtype = itemtypekey
    If strSubAreaName = Empty Then
        strSQL = "Select NOME_ITEM from ITEM where ID_TIPO_ITEM = " & itemTypeKey & " ORDER BY NOME_ITEM"
    Else
        subAreaKey = getSubAreaKey(strSubAreaName)
        strSQL = "Select NOME_ITEM from ITEM where ID_TIPO_ITEM = " & itemTypeKey & "and ID_SUB_ARE = " & subAreaKey & " ORDER BY NOME_ITEM"
    End If
    rs.Open strSQL, gCnn

    ' Adding the Item names into the combo
    If rs.EOF = True Then
        MsgBox "You have no item of the selected type!"
        Exit Sub
    End If

    Do While rs.EOF <> True
        cmbItemName.AddItem rs.Fields("NOME_ITEM").value
        rs.MoveNext
    Loop
    ' Voilá
    On Error GoTo 0

    Exit Sub

populateItems_Error:
    Call handleMyError
End Sub

Public Sub populateItemType(cmbItemType, Optional strItemClassName As String)
'=======================================================================================
' < descrição da rotina >
'---------------------------------------------------------------------------------------
' < descrição dos argumentos>
'---------------------------------------------------------------------------------------
' < Observações >
'---------------------------------------------------------------------------------------
' < Histórico de revisões>
'=======================================================================================
'
' The following code populates the item type combobox with item_type's name

' Declarations
    Dim strSQL                               As String

    ' And i create the recordset to receive the query
    Set rs = New ADODB.Recordset
    Set colDictionary = createTrackingDictionary()



    ' Here i put the command for the query, filtering for the specifications
    If strItemClassName <> Empty Then
        itemClassKey = getItemClassKey(strItemClassName)
        strSQL = "select NOME_TIPO_ITEM from TIPO_ITEM where ID_CLASSE_TIPO_ITEM = " & itemClassKey & " order by NOME_TIPO_ITEM"
    Else
        strSQL = "Select NOME_TIPO_ITEM from TIPO_ITEM ORDER BY NOME_TIPO_ITEM "
    End If

    ' Here i open the query in the recordset rs
    rs.Open strSQL, gCnn

    'Now, I iterate over the query and fill the value of each item type in the combo
    Do While rs.EOF <> True
        cmbItemType.AddItem (rs.Fields("NOME_TIPO_ITEM").value)
        rs.MoveNext
    Loop
End Sub

Public Sub populateItemClass(cmbItemClass)
'=======================================================================================
' < descrição da rotina >
'---------------------------------------------------------------------------------------
' < descrição dos argumentos>
'---------------------------------------------------------------------------------------
' < Observações >
'---------------------------------------------------------------------------------------
' < Histórico de revisões>
'=======================================================================================
'
' The following code populates the item type combobox with item_type's name

' Declarations
    Dim strSQL                               As String

    ' And i create the recordset to receive the query
    Set rs = New ADODB.Recordset
    Set colDictionary = createTrackingDictionary()

    ' Here i put the command for the query,
    strSQL = "Select NOME_CLASSE_TIPO_ITEM from CLASSE_TIPO_ITEM ORDER BY NOME_CLASSE_TIPO_ITEM"

    ' Here i open the query in the recordset rs
    rs.Open strSQL, gCnn

    'Now, I iterate over the query and fill the value of each item type in the combo
    Do While rs.EOF <> True
        cmbItemClass.AddItem (rs.Fields("NOME_CLASSE_TIPO_ITEM").value)
        rs.MoveNext
    Loop
End Sub

Public Sub populateShares(strItemName As String, cmbShares, Optional strPropNameShared As String)
'=======================================================================================
' < descrição da rotina >
'---------------------------------------------------------------------------------------
' < descrição dos argumentos>
'---------------------------------------------------------------------------------------
' < Observações >
'---------------------------------------------------------------------------------------
' < Histórico de revisões>
'=======================================================================================
'
' The following code populates the item type combobox with item_type's name

' Declarations
    Dim rs                                   As ADODB.Recordset
    Dim strSQL                               As String
    Dim strInsideQuery                       As String
    Dim itemKey                              As Long
    Dim propKey                              As Long

    On Error GoTo populateShares_Error

    ' And i create the recordset to receive the query
    Set rs = New ADODB.Recordset
    rs.CursorLocation = adUseClient

    ' getting itemKey from name
    itemKey = getItemKey(strItemName)

    ' Here i put the command for the query
    If strPropNameShared <> "" Then
        propKey = getPropKey(strPropNameShared)

        strInsideQuery = "(select ID_VALOR from LINK_VALORES inner join ITEM on ITEM.ID_ITEM = LINK_VALORES.ID_ITEM" & _
                         " where LINK_VALORES.ID_ITEM = " & itemKey & " and LINK_VALORES.ID_TIPO_PROP = " & propKey & ")"

        strSQL = "select ITEM.NOME_ITEM,ITEM.ID_ITEM,LINK_VALORES.ID_TIPO_PROP " & _
                 "from (LINK_VALORES inner join ITEM on ITEM.ID_ITEM = LINK_VALORES.ID_ITEM) " & _
                 "where ID_VALOR in " & strInsideQuery
    Else
        strInsideQuery = "(select ID_VALOR from LINK_VALORES inner join ITEM on ITEM.ID_ITEM = LINK_VALORES.ID_ITEM" & _
                         " where LINK_VALORES.ID_ITEM = " & itemKey & ")"

        strSQL = "select ITEM.NOME_ITEM,ITEM.ID_ITEM,LINK_VALORES.ID_TIPO_PROP " & _
                 "from (LINK_VALORES inner join ITEM on ITEM.ID_ITEM = LINK_VALORES.ID_ITEM) " & _
                 "where ID_VALOR in " & strInsideQuery & " and ITEM.ID_ITEM <> " & itemKey
    End If

    ' Here i open the query in the recordset rs
    rs.Open strSQL, gCnn

    'Now, I iterate over the query and fill the value of each item type in the combo
    Do While rs.EOF <> True
        If Not (rs.Fields("ID_ITEM").value = itemKey And _
                rs.Fields("ID_TIPO_PROP").value = propKey) Then
            cmbShares.AddItem (rs.Fields("NOME_ITEM").value)
        End If
        rs.MoveNext
    Loop
    On Error GoTo 0

    Exit Sub

populateShares_Error:
    Call handleMyError
End Sub

Public Sub populateProps(strItemTypeName As String, cmbPropName, Optional strPropClass As String)
'=======================================================================================
' < descrição da rotina >
'---------------------------------------------------------------------------------------
' < descrição dos argumentos>
'---------------------------------------------------------------------------------------
' < Observações >
'---------------------------------------------------------------------------------------
' < Histórico de revisões>
'=======================================================================================
'
' The following code populates the comboboxes with item's names and prop's names

' Declarations
    Dim rs                                   As ADODB.Recordset
    Dim strSQL                               As String
    Dim itemTypeKey                          As Long
    Dim propClassKey                         As Long

    ' And i create the recordset to receive the query
    Set rs = New ADODB.Recordset

    ' Getting the keys
    itemTypeKey = getItemTypeKey(strItemTypeName)

    ' POPULATING THE PROPERTY COMBOBOX

    ' Now, I query over all item's properties where item.itemtype = itemtypekey
    ' Getting the item type primary key
    If strPropClass = Empty Then
        strSQL = " SELECT PROPRIEDADES_ITEMS.ID_TIPO_ITEM, TIPO_PROPRIEDADES.NOME_TIPO_PROP, PROPRIEDADES_ITEMS.ID_TIPO_PROP" & _
                 " FROM TIPO_PROPRIEDADES INNER JOIN PROPRIEDADES_ITEMS ON TIPO_PROPRIEDADES.ID_TIPO_PROP = PROPRIEDADES_ITEMS.ID_TIPO_PROP" & _
                 " WHERE (((PROPRIEDADES_ITEMS.ID_TIPO_ITEM)= " & itemTypeKey & "))" & _
                 " ORDER BY TIPO_PROPRIEDADES.NOME_TIPO_PROP "
    Else
        propClassKey = getPropClassKey(strPropClass)
        strSQL = " SELECT PROPRIEDADES_ITEMS.ID_TIPO_ITEM, TIPO_PROPRIEDADES.NOME_TIPO_PROP, PROPRIEDADES_ITEMS.ID_TIPO_PROP" & _
                 " FROM TIPO_PROPRIEDADES INNER JOIN PROPRIEDADES_ITEMS ON TIPO_PROPRIEDADES.ID_TIPO_PROP = PROPRIEDADES_ITEMS.ID_TIPO_PROP" & _
                 " WHERE PROPRIEDADES_ITEMS.ID_TIPO_ITEM= " & itemTypeKey & " AND TIPO_PROPRIEDADES.ID_CLASSE_TIPO_PROP = " & propClassKey & _
                 " ORDER BY TIPO_PROPRIEDADES.NOME_TIPO_PROP "
    End If
    rs.Open strSQL, gCnn

    ' Adding the fields from the table into the combo
    On Error Resume Next
    rs.MoveFirst
    Do While rs.EOF <> True
        cmbPropName.AddItem rs.Fields("NOME_TIPO_PROP").value
        rs.MoveNext
    Loop
    On Error GoTo 0
End Sub

Public Sub populateExistantProps(strItemName As String, cmbPropName, Optional strPropClass As String)
'=======================================================================================
' < descrição da rotina >
'---------------------------------------------------------------------------------------
' < descrição dos argumentos>
'---------------------------------------------------------------------------------------
' Aqui eu assumo que o campo ID_VALOR tem participação obrigatória na tabela LINK_VALORES
'---------------------------------------------------------------------------------------
' < Histórico de revisões>
'=======================================================================================
'
' The following code populates the comboboxes with item's names and prop's names

' Declarations
    Dim rs                                   As ADODB.Recordset
    Dim strSQL                               As String
    Dim itemKey                              As Long
    Dim propClassKey                         As Long

    ' And i create the recordset to receive the query
    Set rs = New ADODB.Recordset

    ' Getting itemTypeKey
    itemKey = getItemKey(strItemName)
    itemTypeKey = getItemTypeFromItemKey(itemKey)

    ' POPULATING THE PROPERTY COMBOBOX

    ' Now, I query over all item's properties where item.itemtype = itemtypekey
    ' Getting the item type primary key
    If strPropClass = Empty Then
        strSQL = " select TIPO_PROPRIEDADES.NOME_TIPO_PROP" & _
                 " from TIPO_PROPRIEDADES inner join LINK_VALORES on LINK_VALORES.ID_TIPO_PROP = TIPO_PROPRIEDADES.ID_TIPO_PROP" & _
                 " where LINK_VALORES.ID_ITEM = " & itemKey & ";" & _
                 " union" & _
                 " select NOME_TIPO_PROP FROM (TIPO_PROPRIEDADES inner join PROPRIEDADES_ITEMS on PROPRIEDADES_ITEMS.ID_TIPO_PROP = TIPO_PROPRIEDADES.ID_TIPO_PROP) " & _
                 " where TIPO_PROPRIEDADES.ID_CLASSE_TIPO_PROP = " & calculatedPropClassKey & " and PROPRIEDADES_ITEMS.ID_TIPO_ITEM = " & itemTypeKey & ";"
    Else
        propClassKey = getPropClassKey(strPropClass)
        If propClassKey <> calculatedPropClassKey Then
            strSQL = "Select NOME_TIPO_PROP from (TIPO_PROPRIEDADES inner join PROPRIEDADES_ITEMS on TIPO_PROPRIEDADES.ID_TIPO_PROP = PROPRIEDADES_ITEMS.ID_TIPO_PROP) " & _
                     " left join LINK_VALORES on PROPRIEDADES_ITEMS.ID_TIPO_PROP = LINK_VALORES.ID_TIPO_PROP" & _
                     " where TIPO_PROPRIEDADES.ID_CLASSE_TIPO_PROP = " & propClassKey & _
                     " and LINK_VALORES.ID_ITEM = " & itemKey
        Else
            strSQL = "Select NOME_TIPO_PROP from (TIPO_PROPRIEDADES inner join PROPRIEDADES_ITEMS on TIPO_PROPRIEDADES.ID_TIPO_PROP = PROPRIEDADES_ITEMS.ID_TIPO_PROP) " & _
                     " left join LINK_VALORES on PROPRIEDADES_ITEMS.ID_TIPO_PROP = LINK_VALORES.ID_TIPO_PROP" & _
                     " where TIPO_PROPRIEDADES.ID_CLASSE_TIPO_PROP = " & propClassKey
        End If
    End If

    rs.Open strSQL, gCnn

    ' Adding the fields from the table into the combo
    On Error Resume Next
    rs.MoveFirst
    Do While rs.EOF <> True
        cmbPropName.AddItem rs.Fields("NOME_TIPO_PROP").value
        rs.MoveNext
    Loop
    On Error GoTo 0
End Sub

Public Sub populateSharedProps(strItemName As String, cmbPropName, Optional strPropClass As String)
'=======================================================================================
' < descrição da rotina >
'---------------------------------------------------------------------------------------
' < descrição dos argumentos>
'---------------------------------------------------------------------------------------
' < Observações >
'---------------------------------------------------------------------------------------
' < Histórico de revisões>
'=======================================================================================
'
' The following code populates the comboboxes with item's names and prop's names

' Declarations
    Dim rs                                   As ADODB.Recordset
    Dim strSQL                               As String
    Dim itemTypeKey                          As Long
    Dim propClassKey                         As Long
    Dim propKey                              As Long
    Dim itemKey                              As Long

    ' And i create the recordset to receive the query
    Set rs = New ADODB.Recordset
    rs.CursorLocation = adUseClient

    ' Getting the keys
    itemKey = getItemKey(strItemName)
    itemTypeKey = getItemTypeFromItemKey(itemKey)

    ' POPULATING THE PROPERTY COMBOBOX

    ' Now, I query over all item's properties where item.itemtype = itemtypekey
    ' Getting the item type primary key
    If strPropClass = Empty Then
        strSQL = " SELECT PROPRIEDADES_ITEMS.ID_TIPO_ITEM, TIPO_PROPRIEDADES.NOME_TIPO_PROP, PROPRIEDADES_ITEMS.ID_TIPO_PROP" & _
                 " FROM TIPO_PROPRIEDADES INNER JOIN PROPRIEDADES_ITEMS ON TIPO_PROPRIEDADES.ID_TIPO_PROP = PROPRIEDADES_ITEMS.ID_TIPO_PROP" & _
                 " WHERE (((PROPRIEDADES_ITEMS.ID_TIPO_ITEM)= " & itemTypeKey & "))" & _
                 " ORDER BY TIPO_PROPRIEDADES.NOME_TIPO_PROP "
    Else
        propClassKey = getPropClassKey(strPropClass)
        strSQL = " SELECT PROPRIEDADES_ITEMS.ID_TIPO_ITEM, TIPO_PROPRIEDADES.NOME_TIPO_PROP, PROPRIEDADES_ITEMS.ID_TIPO_PROP" & _
                 " FROM TIPO_PROPRIEDADES INNER JOIN PROPRIEDADES_ITEMS ON TIPO_PROPRIEDADES.ID_TIPO_PROP = PROPRIEDADES_ITEMS.ID_TIPO_PROP" & _
                 " WHERE PROPRIEDADES_ITEMS.ID_TIPO_ITEM= " & itemTypeKey & " AND TIPO_PROPRIEDADES.ID_CLASSE_TIPO_PROP = " & propClassKey & _
                 " ORDER BY TIPO_PROPRIEDADES.NOME_TIPO_PROP "
    End If
    rs.Open strSQL, gCnn

    ' Adding the fields from the table into the combo
    On Error Resume Next
    rs.MoveFirst
    Do While rs.EOF <> True
        propKey = rs.Fields("ID_TIPO_PROP").value
        If checkIfIsShared(itemKey, propKey) Then
            cmbPropName.AddItem rs.Fields("NOME_TIPO_PROP").value
        End If
        rs.MoveNext
    Loop
    On Error GoTo 0
End Sub

Public Sub populateTrackingProps(strItemTypeName As String, cmbTrackingPropName)
'=======================================================================================
' < descrição da rotina >
'---------------------------------------------------------------------------------------
' < descrição dos argumentos>
'---------------------------------------------------------------------------------------
' < Observações >
'---------------------------------------------------------------------------------------
' < Histórico de revisões>
'=======================================================================================
'
' Declarations
    Dim rs                                   As ADODB.Recordset
    Dim strSQL                               As String
    Dim itemTypeKey                          As Long
    Dim colDictionary                        As Collection
    Dim field                                As Variant
    Dim propToAdd                            As String

    On Error GoTo populateTrackingProps_Error

    ' And i create the recordset to receive the query
    Set rs = New ADODB.Recordset

    ' Getting itemTypeKey
    itemTypeKey = getItemTypeKey(strItemTypeName)

    ' For visual porpuses only, I create this collection to translate the field names
    Set colDictionary = New Collection
    Set colDictionary = createTrackingDictionary()

    ' Now, I get the whole table of all the tracking properties of this item (The parent's general properties)
    strSQL = "select ITEM.NOME_ITEM, SUB_AREA.NOME_SUB_ARE, AREA.NOME_ARE, PLANTA.NOME_PLA, INDUSTRIAL.NOME_IND, UNIDADE_NEGOCIO.NOME_UNI " & _
             "from UNIDADE_NEGOCIO INNER JOIN ((((INDUSTRIAL INNER JOIN PLANTA ON INDUSTRIAL.ID_IND = PLANTA.ID_IND) INNER JOIN AREA ON " & _
             "PLANTA.ID_PLA = AREA.ID_PLA) INNER JOIN SUB_AREA ON AREA.ID_ARE = SUB_AREA.ID_ARE) INNER JOIN ITEM ON SUB_AREA.ID_SUB_ARE = ITEM.ID_SUB_ARE) ON UNIDADE_NEGOCIO.ID_UNI = INDUSTRIAL.ID_UNI " & _
             "where ITEM.ID_TIPO_ITEM = " & itemTypeKey

    ' Now, I open this query
    rs.Open strSQL, gCnn

    For Each field In rs.Fields
        propToAdd = colDictionary(field.Name)
        cmbTrackingPropName.AddItem (propToAdd)
    Next field
    On Error GoTo 0

    Exit Sub

populateTrackingProps_Error:
    Call handleMyError

End Sub

Public Sub populateSubArea(cmbSubArea)
'=======================================================================================
' < descrição da rotina >
'---------------------------------------------------------------------------------------
' < descrição dos argumentos>
'---------------------------------------------------------------------------------------
' < Observações >
'---------------------------------------------------------------------------------------
' < Histórico de revisões>
'=======================================================================================
'
' The following code populates the comboboxes with item's names and prop's names

' Declarations
    Dim rs                                   As ADODB.Recordset
    Dim strSQL                               As String

    On Error GoTo populateSubArea_Error

    ' And i create the recordset to receive the query
    Set rs = New ADODB.Recordset

    ' Now, I query over all item's where item.itemtype = itemtypekey
    strSQL = "Select NOME_SUB_ARE from SUB_AREA"
    rs.Open strSQL, gCnn

    ' checking keyness
    Call checkKeyness(rs)

    Do While rs.EOF <> True
        cmbSubArea.AddItem rs.Fields("NOME_SUB_ARE").value
        rs.MoveNext
    Loop
    ' Voilá
    On Error GoTo 0

    Exit Sub

populateSubArea_Error:
    Call handleMyError
End Sub

Public Sub populatePropClass(cmbPropClass)
'=======================================================================================
' < descrição da rotina >
'---------------------------------------------------------------------------------------
' < descrição dos argumentos>
'---------------------------------------------------------------------------------------
' < Observações >
'---------------------------------------------------------------------------------------
' < Histórico de revisões>
'=======================================================================================
'
' The following code populates the comboboxes with item's names and prop's names

' Declarations
    Dim rs                                   As ADODB.Recordset
    Dim strSQL                               As String

    On Error GoTo populatePropClass_Error

    ' And i create the recordset to receive the query
    Set rs = New ADODB.Recordset

    ' Now, I query over all item's where item.itemtype = itemtypekey
    strSQL = "Select NOME_CLASSE_TIPO_PROP from CLASSE_TIPO_PROP"
    rs.Open strSQL, gCnn
    ' Adding the Item names into the combo
    If rs.EOF = True Then
        MsgBox "You have no Sub Area's in the database!"
        Exit Sub
    End If

    Do While rs.EOF <> True
        cmbPropClass.AddItem rs.Fields("NOME_CLASSE_TIPO_PROP").value
        rs.MoveNext
    Loop
    ' Voilá
    On Error GoTo 0

    Exit Sub

populatePropClass_Error:
    Call handleMyError
End Sub

Public Sub populateUnits(strPropName As String, cmbUnits)
'=======================================================================================
' < descrição da rotina >
'---------------------------------------------------------------------------------------
' < descrição dos argumentos>
'---------------------------------------------------------------------------------------
' < Observações >
'---------------------------------------------------------------------------------------
' < Histórico de revisões>
'=======================================================================================
'
' The following code populates the comboboxes with item's names and prop's names

' Declarations
    Dim unitNameCol                          As Collection
    Dim dimKey                               As Long
    Dim propKey                              As Long
    Dim tempUnit                             As unit

    propKey = getPropKey(strPropName)
    dimKey = getDimKey(propKey)

    If dimKey <> 0 Then
        On Error GoTo populateUnits_Error

        For Each tempUnit In gUnitDef.pUnitCollection
            If tempUnit.dimension = dimKey Then
                cmbUnits.AddItem tempUnit.symbol
            End If
        Next tempUnit
    End If

    ' Voilá
    On Error GoTo 0

    Exit Sub

populateUnits_Error:
    Call handleMyError
End Sub

Public Sub populateSavedShares(cmbSavedShares, strItemType1 As String, strItemType2 As String)
    Dim itemTypeKey1                         As Long
    Dim itemTypeKey2                         As Long
    Dim objXml                               As MSXML2.DOMDocument
    Dim objNodeSet                           As MSXML2.IXMLDOMNodeList
    Dim j                                    As Integer

    ' getting the type keys
    itemTypeKey1 = getItemTypeKey(strItemType1)
    itemTypeKey2 = getItemTypeKey(strItemType2)

    Call populateSavedSharesFromKeys(cmbSavedShares, itemTypeKey1, itemTypeKey2)
End Sub

Public Sub populateSavedSharesFromKeys(cmbSavedShares, itemTypeKey1 As Long, itemTypeKey2 As Long)
' getting the xml document
    Set objXml = New MSXML2.DOMDocument
    If False = objXml.Load(getSharesXmlPath()) Then
        MsgBox "Redefina a localização do xml de configuração dos compartilhamentos"
        storeSharesXmlPath (getFileDialog())
        objXml.Load (getSharesXmlPath())
    End If

    Set objNodeSet = objXml.getElementsByTagName("share")

    For j = 0 To objNodeSet.Length - 1
        If objNodeSet.Item(j).SelectSingleNode("typePair").SelectSingleNode("type1").Text = itemTypeKey1 And _
           objNodeSet.Item(j).SelectSingleNode("typePair").SelectSingleNode("type2").Text = itemTypeKey2 Then
            cmbSavedShares.AddItem objNodeSet.Item(j).SelectSingleNode("name").Text
        End If
    Next j
End Sub

Public Sub addToShareList(shareList As ListBox, strItemName1 As String, strItemName2 As String, _
                          strPropName1 As String, strPropName2 As String)
' Adding to the list.
    shareList.AddItem strItemName1
    shareList.List(shareList.ListCount - 1, 1) = strItemName2
    shareList.AddItem strPropName1
    shareList.List(shareList.ListCount - 1, 1) = strPropName2
    shareList.AddItem "----------------"
    shareList.List(shareList.ListCount - 1, 1) = "---------------"
End Sub

Public Sub removeFromShareList(shareList As ListBox, indexClicked As Integer)
    For j = 1 To 3
        shareList.RemoveItem (3 * indexClicked)
    Next j
End Sub

Public Function loadShareCollection(strShareName As String, strItemName1 As String, strItemName2 As String) As shareQueue
    Dim objXml           As MSXML2.DOMDocument
    Dim objXmlShareNode  As MSXML2.IXMLDOMNode
    Dim objXmlNodes      As MSXML2.IXMLDOMNodeList
    Dim propKey1         As Long
    Dim propKey2         As Long
    Dim strPropName1     As String
    Dim strPropName2     As String
    Dim j                As Integer
    Dim tempQueue        As shareQueue

    Set tempQueue = New shareQueue

    Set objXml = New MSXML2.DOMDocument
    If False = objXml.Load(getSharesXmlPath) Then
        MsgBox "Redefina a localização do xml de configuração dos compartilhamentos"
        storeSharesXmlPath (getFileDialog())
        objXml.Load (getSharesXmlPath())
    End If

    Set objXmlShareNode = objXml.SelectSingleNode("//share[name=" & Chr(34) & strShareName & Chr(34) & "]/propPairSet")
    Set objXmlNodes = objXmlShareNode.SelectNodes("propPair")

    For j = 0 To objXmlNodes.Length - 1
        propKey1 = objXmlNodes.Item(j).SelectSingleNode("prop1").Text
        propKey2 = objXmlNodes.Item(j).SelectSingleNode("prop2").Text

        strPropName1 = getPropName(propKey1)
        strPropName2 = getPropName(propKey2)

        Call tempQueue.enqueue(strItemName1, strPropName1, strItemName2, strPropName2)
    Next j

    Set loadShareCollection = tempQueue

End Function

Attribute VB_Name = "ztestSubs"
' Chemtech - A Siemens Business ========================================================
'
'=======================================================================================
Option Explicit
' Desenvolvimento ======================================================================
' <iniciais>            Renan       <email>
'=======================================================================================
' Versões ==============================================================================
'
'
'
'=======================================================================================

Public Sub runTestSuite()
'=======================================================================================
' < descrição da rotina >
'---------------------------------------------------------------------------------------
' < descrição dos argumentos>
'---------------------------------------------------------------------------------------
' < Observações >
'---------------------------------------------------------------------------------------
' < Histórico de revisões>
'=======================================================================================
'
    MsgBox "iniciando teste de tratamento de erro controlado"
    Call testCustomErrorCatch
    MsgBox "iniciando teste de tratamento de erro não tratado"
    Call testErrorCatch
    MsgBox "iniciando teste do getData"
    Call testGetDataError
    MsgBox "iniciando teste de existência de valor"
    Call testValueExistance
    MsgBox "iniciando teste de upload de dado simples"
    Call upload_dado
    MsgBox "iniciando teste de compartilhamento e quebra"
    Call testeShare
    MsgBox "iniciando teste de update de propriedade de rastreamento"
    Call test_track_change
End Sub

Private Sub testErrorCatch()
'=======================================================================================
' < descrição da rotina >
'---------------------------------------------------------------------------------------
' < descrição dos argumentos>
'---------------------------------------------------------------------------------------
' < Observações >
'---------------------------------------------------------------------------------------
' < Histórico de revisões>
'=======================================================================================
'
    Dim a                                    As Single
    On Error GoTo testErrorCatch_Error
    a = 1 / 0

    Exit Sub

testErrorCatch_Error:
    Call handleMyError

End Sub

Private Sub testCustomErrorCatch()
'=======================================================================================
' < descrição da rotina >
'---------------------------------------------------------------------------------------
' < descrição dos argumentos>
'---------------------------------------------------------------------------------------
' < Observações >
'---------------------------------------------------------------------------------------
' < Histórico de revisões>
'=======================================================================================
'
    On Error GoTo testCustomErrorCatch_Error
    Err.Raise Number:=vbObjectError + 22000, Description:="Caught your test error"

    Exit Sub

testCustomErrorCatch_Error:
    Call handleMyError
End Sub

Private Sub testGetDataError()

    Dim strAddress                           As String
    Dim resultado                            As String

    'item que não existe
    strAddress = "dummy1345dummyD3867567"
    resultado = getData(strAddress, True)
    MsgBox "Resultado = " & resultado

    'item que existe
    strAddress = "dummy3dummyD7"
    resultado = getData(strAddress, True)
    MsgBox "Resultado = " & resultado

End Sub

Private Sub testValueExistance()

    Dim itemKey                              As Long
    Dim propKey                              As Long

    itemKey = -115
    propKey = -19

    If Not checkValueExistance(itemKey, propKey) Then
        MsgBox "teste concluido com sucesso"
    Else
        MsgBox "vishhhhh, ta errado", vbCritical
    End If
End Sub


Private Sub upload_dado()
'=======================================================================================
' < descrição da rotina >
'---------------------------------------------------------------------------------------
' < descrição dos argumentos>
'---------------------------------------------------------------------------------------
' < Observações >
'---------------------------------------------------------------------------------------
' < Histórico de revisões>
'=======================================================================================
'

    Dim itemName                             As String
    Dim itemType                             As String
    Dim propName                             As String
    Dim value                                As String
    Dim unit                                 As String
    Dim itemExists                           As Boolean
    Dim itemKey                              As Long
    Dim propKey                              As Long
    Dim valueKey                             As Long

    'start
    itemName = "BA-050234"
    itemType = "BOMBA"
    propName = "CALOR ESPECIFICO"
    value = Rnd()
    unit = 0

    itemExists = checkItemExistance(itemName)

    If Not itemExists Then
        Call createItem(itemName, itemType, "SUB AREA1")
        If Err Then MsgBox "erro na criação do item"
    End If

    itemKey = getItemKey(itemName)
    propKey = getPropKey(propName)
    valueKey = getValueKey(itemKey, propKey)

    'Teste de inserção de um dado
    Call exportSingleData(itemName, propName, value, unit, True)

    Debug.Assert value = getValue(valueKey)

    ' report
    If Not Err Then
        MsgBox "teste executado com sucesso"
    Else
        MsgBox "teste não foi concluido com sucesso", vbCritical
    End If

End Sub

Private Sub testeShare()
'=======================================================================================
' < descrição da rotina >
'---------------------------------------------------------------------------------------
' < descrição dos argumentos>
'---------------------------------------------------------------------------------------
' < Observações >
'---------------------------------------------------------------------------------------
' < Histórico de revisões>
'=======================================================================================
'

    Dim name1                                As String
    Dim name2                                As String
    Dim prop1                                As String
    Dim prop2                                As String
    Dim value1                               As String
    Dim value2                               As String
    Dim unit1                                As String
    Dim unit2                                As String
    Dim itemKey1                             As Long
    Dim itemKey2                             As Long
    Dim propKey1                             As Long
    Dim propKey2                             As Long
    Dim valKey1                              As Long
    Dim valKey2                              As Long
    Dim result1                              As String
    Dim result2                              As String


    name1 = "10-HT-107"
    name2 = "10-HT-108"
    prop1 = "AREA"
    prop2 = "AREA"
    value1 = "12"
    value2 = "24"
    unit1 = "m²"
    unit2 = "m¹"

    ' getting keys to check if the thing was created
    itemKey1 = getItemKey(name1)
    itemKey2 = getItemKey(name2)
    propKey1 = getPropKey(prop1)
    propKey2 = getPropKey(prop2)

    ' getting the values after sharing
    valKey1 = getValueKey(itemKey1, propKey1)
    valKey2 = getValueKey(itemKey2, propKey2)

    ' if they are already shared, break the sharing
    If valKey1 = valKey2 Then
        Call breakSharing(name1, prop1, name2, prop2)
        ' getting the values after sharing
        valKey1 = getValueKey(itemKey1, propKey1)
        valKey2 = getValueKey(itemKey2, propKey2)
    End If

    ' putting two different values there
    Call exportSingleData(name1, prop1, value1, unit1)
    Call exportSingleData(name2, prop2, value2, unit2)

    Debug.Print getValue(valKey2)
    Debug.Print getValue(valKey1)
    Debug.Assert (getValue(valKey1) <> getValue(valKey2))

    ' creating the sharing
    Call createSharing(name1, prop1, name2, prop2)

    ' getting the values after sharing
    valKey1 = getValueKey(itemKey1, propKey1)
    valKey2 = getValueKey(itemKey2, propKey2)

    ' asserting that the sharing did happen
    result1 = getValue(valKey1)
    result2 = getValue(valKey2)
    Debug.Assert (valKey1 = valKey2)
    Debug.Assert (result1 = result2)

    ' breaking the sharing
    Call breakSharing(name1, prop1, name2, prop2)

    ' getting the values after the break
    valKey1 = getValueKey(itemKey1, propKey1)
    valKey2 = getValueKey(itemKey2, propKey2)

    ' asserting that the sharing was broke
    Debug.Assert (valKey1 <> valKey2)
    Debug.Assert (getValue(valKey1) = getValue(valKey2))

    Debug.Assert (getValue(valKey1) = value1)                  ' this now will only work if you choose yes
    Debug.Assert (getValue(valKey2) = value1)

    If Not Err Then
        MsgBox "teste executado com sucesso"
    Else
        MsgBox "teste não foi concluido com sucesso", vbCritical
    End If
End Sub

Private Sub test_track_change()
'=======================================================================================
' < descrição da rotina >
'---------------------------------------------------------------------------------------
' < descrição dos argumentos>
'---------------------------------------------------------------------------------------
' < Observações >
'---------------------------------------------------------------------------------------
' < Histórico de revisões>
'=======================================================================================
'
    Dim itemName                             As String
    Dim itemKey                              As Long
    Dim newName                              As String
    Dim propName                             As String


    ' itemName
    itemName = "10-HT-108"

    ' start of the testing
    itemKey = getItemKey(itemName)
    newName = "NOMENOVO"
    propName = "Nome do item"

    ' changing
    Call changeTrackingData(itemName, propName, newName)

    ' checking change
    MsgBox getItemName(itemKey) & "  o certo aqui é: " & newName

    ' undoing the change
    Call changeTrackingData(newName, propName, itemName)

    ' checking change
    MsgBox getItemName(itemKey) & "  o certo aqui é: " & itemName
End Sub



Private Sub test_query()
'=======================================================================================
' < descrição da rotina >
'---------------------------------------------------------------------------------------
' < descrição dos argumentos>
'---------------------------------------------------------------------------------------
' < Observações >
'---------------------------------------------------------------------------------------
' < Histórico de revisões>
'=======================================================================================
'
    Dim rs                                   As ADODB.Recordset
    Set rs = getQuery("viewItemProp")
    Call query2msgbox(rs)

End Sub

Private Function getQuery(strQueryName As String) As ADODB.Recordset
'=======================================================================================
' < descrição da rotina >
'---------------------------------------------------------------------------------------
' < descrição dos argumentos>
'---------------------------------------------------------------------------------------
' < Observações >
'---------------------------------------------------------------------------------------
' < Histórico de revisões>
'=======================================================================================
'
    Dim strConnect                           As String
    Dim rs                                   As ADODB.Recordset
    Dim cnn                                  As ADODB.Connection

    gCnn.Open strConnect

    ' And i create the recordset to receive the query
    Set rs = New ADODB.Recordset

    rs.Open strQueryName, cnn

    Set getQuery = rs
End Function

Private Sub query2msgbox(rs As ADODB.Recordset)
'=======================================================================================
' < descrição da rotina >
'---------------------------------------------------------------------------------------
' < descrição dos argumentos>
'---------------------------------------------------------------------------------------
' < Observações >
'---------------------------------------------------------------------------------------
' < Histórico de revisões>
'=======================================================================================
'
    Dim strReport                            As String
    Dim field                                As Variant

    strReport = ""
    For Each field In rs.Fields
        strReport = strReport & field.Name & "   "
    Next field

    strReport = strReport & vbCr

    Do While rs.EOF <> True
        For Each field In rs.Fields
            strReport = strReport & " | " & field.value
        Next field

        strReport = strReport & " | " & vbCr

        rs.MoveNext
    Loop
    MsgBox strReport
End Sub
